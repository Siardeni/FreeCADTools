# -*- coding:Utf-8 -*-
######################################################
# Programme Python type                              #
# Auteur : Nicolas Tuffereau, Angers, decembre 2015  #
# Licence : GPL                                      #
######################################################


# Reste à faire 
#
#--------------------
# Cornière profilé à froids
# Tracer la fibre neutre
# Calculer poids et comparer au poid catalogue
# Platine
# Tôles pliées
# Prendre en compte Cornièrer acier au-dela de 200x200 géométrie section différente
# Identifier tube cintrés
# Catalogue Tubes carrés et rectangles alu et acier


#--------------------


#####################################
# Importation de fonctions externes :

#froMos import *
import FreeCAD, FreeCADGui, Part, Draft, math, MeshPart, Mesh, Drawing, DraftGeomUtils, WorkingPlane, importDXF
import DraftVecUtils
import os,Chemin
from FreeCAD import Base
App=FreeCAD
Gui=FreeCADGui

tolerance=0.000001

def show(shape,name='Shape',doc=None):
    if doc is None:
        import FreeCAD
        doc=FreeCAD.activeDocument() or FreeCAD.newDocument()
    obj=doc.addObject("Part::Feature",name.encode('utf-8'))
    obj.Label=name.encode('utf-8')
    obj.Shape=shape
    obj.ViewObject.LineColor = (0.00,1.00,0.00)
    obj.ViewObject.LineWidth = 3.00
    return obj

def comp(v1, v2):
    #fonction utile a xxx.sort(cmp=comp)
    if v1[1]>v2[1]:
        return -1
    elif v1[1]>v2[1]:
        return 1
    else:
        return 0
        
def compinv(v1, v2):
    #fonction utile a xxx.sort(cmp=compinv)
    if v1[1]<v2[1]:
        return -1
    elif v1[1]<v2[1]:
        return 1
    else:
        return 0

def Ln(Edges):
    #Tri les arrêtes par longeurs en excluant les arrêtes courbées
    
    Ln=[]
    L=0
    n=0
    for edge in Edges:
        if edge.curvatureAt(0.0)<=tolerance:
            L=edge.Length
            Ln.append([n,L])
        n=n+1
    
    Ln.sort(cmp=comp)
    
    return Ln

def LnCurves(Edges):
    #Tri les arrêtes par longeurs y compris les arrêtes courbées
    Ln=[]
    L=0
    n=0
    for edge in Edges:
        L=edge.Length
        Ln.append([n,L])
        n=n+1

    Ln.sort(cmp=comp)
    
    
    return Ln

def Sn(Faces):
    #Tri les faces par surfaces
    
    Sn=[]
    S=0
    n=0
    for face in Faces:
        S=face.Area
        Sn.append([n,S])
        n=n+1
    
    Sn.sort(cmp=comp)
    
    return Sn

def CreateLine(P1,P2,Show):
    if P1.x==P2.x and P1.y==P2.y and P1.z==P2.z:
        print u"Les coordonnées des points sont identiques. Créations d'une ligne partant de (0,0,0) et allant vers le premier points" 
        X0Y0Z0=Base.Vector(0.0,0.0,0.0)
        L1=Part.makeLine((X0Y0Z0.x,X0Y0Z0.y,X0Y0Z0.z),(P1.x,P1.y,P1.z))
        if Show==1:
            Part.show(L1)
    else:
        Line=Part.makeLine((P1.x,P1.y,P1.z),(P2.x,P2.y,P2.z))
        if Show==1:
            Part.show(Line)
    return

def EdgesAreParallels(EdgeA,EdgeB):
    "contrôle si deux edges sont parallèles"
    VA = (EdgeA.Curve.EndPoint - EdgeA.Curve.StartPoint).normalize()
    VB = (EdgeB.Curve.EndPoint - EdgeB.Curve.StartPoint).normalize()
    if abs((VA.cross(VB)).Length) <= tolerance:
        return True
    else:
        return False
    return

def Serie_Complementaire_Face(Sol,SerieFace):
    "Renvoi pour une série de face d'un solide l'ensemble des autres faces"
    SerieComplementaire=[]
    for face in Sol.Faces:
        test=1
        for faceM in SerieFace:
            if faceM.isEqual(face):
                test=0
        if test==1:
            SerieComplementaire.append(face)
    return SerieComplementaire        
    

def FindFaceWithParallelEdge(solI,facesI,facesINeg,edgeI):
    "Cherche la face dans un solide (sol) qui n'appartient pas à la liste des faces"
    "et qui a une arête parallele à edge"
    "Renvoi la face trouvé l'arête parallèle"
    # "et la liste des faces contenant additionné de la face trouvé"
    #~ print solI.Faces
    faceAdjacent=False
    edgeParallel=False
    for face in facesINeg:
        for edge in face.Edges:
            if edge.isPartner(edgeI):
                #~ print edge.isPartner(edgeI)
                faceAdjacent=face
                #~ show(face,u"facetrouvé")
    if not faceAdjacent==False:
        for face in facesI:
            if faceAdjacent.isEqual(face):
                #~ print "lll2"
                #~ print faceAdjacent.isEqual(face)
                #~ print faceAdjacent.isSame(face)
                #~ print faceAdjacent.isPartner(face)
                #~ show(faceAdjacent,"faceAdjacentpbm")
                #~ show(face,"facepbm")
                faceAdjacent=False
    #~ facesI.append(faceAdjacent)
    distmax=0.0
    nbEdge=0
    #~ print "faceAdjacent"
    #~ print faceAdjacent
    if faceAdjacent!=False:
        for edge in faceAdjacent.Edges:
            if EdgesAreParallels(edgeI,edge)==True:
                dist=edgeI.distToShape(edge)
                #~ print "-------------"
                #~ print "dist"
                #~ print dist[0]
                #~ print "-------------"
                if dist[0]-distmax>tolerance:
                    distmax=dist[0]
                    edgeParallel=faceAdjacent.Edges[nbEdge]
            if distmax<tolerance:
                edgeParallel=False
            nbEdge=nbEdge+1
    return faceAdjacent,edgeParallel#,facesI

def Longueur_Coupe(plaque):
    L=0
    for wire in plaque.Wires:
        L+=wire.Length
    return L

def Construction_Nom_Plaque(plaque):
    Nom=plaque[1]+u'_ep_'+str(plaque[2])+u'_Qté_'#+str(Qte)
    return Nom

def Export_vers_dxf(obj,Nom_fichier):
    os.chdir(Chemin.CheminEchange(1))
    #~ importDXF.export(obj,Nom_fichier+'.dxf')
    filename = Nom_fichier+'.dxf'
    FILE = open(filename,"w")
    dxf_output = "0\nSECTION\n2\nENTITIES\n"
    dxf_output += Drawing.projectToDXF(obj.Shape,Base.Vector(0,0,1))
    #~ for wire in obj.Shape.Wires:
        #~ for edge in wire.Edges:
            #~ dxf_output += Drawing.projectToDXF(edge,Base.Vector(0,0,1))
    dxf_output += "0\nENDSEC\n0\nEOF"
    dxf_output=dxf_output.replace('8\nsheet_layer\n','')
    liste_dxf=dxf_output.split('\n')
    n=0
    for ligne in liste_dxf:
        if ligne.find('e-01')!=-1:
            liste_dxf[n]='0'
        n+=1
    dxf_output='\n'.join(liste_dxf)
    FILE.write(dxf_output)
    FILE.close()


####################################################################
#Copie Macro WorkFeature
####################################################################
#Print a message on console.   
def print_msg(message):
    " Print a message on console."
    print message
    App.Console.PrintMessage( message + "\n")

def print_point(point, msg=u""):
    " Print x,y and z of a point:vector."
    if point.__class__.__name__ != "Vector":
        print_msg("Not a Vector to print !")
        return
    #print_msg(str(point))
    #m_type = point.__class__.__name__
    #print_msg(str(m_type))
    print_msg(str(msg) +
              u"x =" + str(point.x).encode('utf-8') + ", "
              u"y =" + str(point.y).encode('utf-8') + ", "
              u"z =" + str(point.z).encode('utf-8'))
    return

def centerLinePoint(edge,info=0):
    " Return the center point of the Line."
    center = None
    #VVector_A=edge.valueAt( 0.0 )
    Vector_A = edge.Vertexes[0].Point
    if info != 0:
        print_point(Vector_A,"Origin of line selected is : ") 
    #Vector_B=edge.valueAt( edge.Length )
    Vector_B = edge.Vertexes[-1].Point
    if info != 0:
        print_point(Vector_B,"End of line selected is : ") 
    Vector_MidPoint = Vector_B + Vector_A
    center = Vector_MidPoint.multiply(0.5)
    if info != 0:
        print_point(center,"Center of line selected is : ") 
    return center

def intersecPerpendicularLine(A, B, C, info=0):
    """ Return the intersection between the Line L defined by A and B
    and the Line perpendicular crossing the point C.
    """
    # L is the line defined by 2 points A(ax, ay, az) and B(bx, by, bz), and
    # may be also defined as the line crossing A(ax, ay, az) and along the 
    # direction AB = U(bx-ax, by-ay, bz-az)
    # If U(ux, uy, uz) = U(bx-ax, by-ay, bz-az) the Line L is the set of 
    # points M as defined by eq(1):
    # Vector(MA) = k * Vector(U)
    # with k Real 
    if A == B:
        return None
    ax, ay, az = A.x, A.y, A.z
    bx, by, bz = B.x, B.y, B.z
    cx, cy, cz = C.x, C.y, C.z
    ux, uy, uz = bx - ax, by - ay, bz - az
    #U = App.Vector(ux, uy, uz)
    # We look for T(tx, ty, tz) on the Line L
    # eq(1) in parametric form; k exists and follows eq(2):
    # tx = ax + k * ux 
    # ty = ay + k * uy
    # tz = az + k * uz
    
    # and vector V(vx, vy, vz) defined by point C and point T
    # vx, vy, vz = tx - cx, ty - cy, tz - cz
    # V must be perpendicular to the Line L 
    # We consider Dot product between U and V and give us eq(3) 
    # U.V = 0
    # so ux * vx + uy * vy + uz * vz = 0
    # ux * (tx - cx) + uy * (ty - cy) + uz * (tz - cz) = 0
    # ux * (ax + k * ux  - cx) + uy * (ay + k * uy - cy) + uz * (az + k * uz  - cz) = 0
    # ux*ax + ux*(k*ux) - ux*cx + uy*ay + uy*(k*uy) - uy*cy +  uz*az + uz*(k*uz) - uz*cz = 0
    if (ux*ux + uy*uy + uz*uz) == 0.0:
        return None
    k = (ux*cx + uy*cy + uz*cz - ux*ax - uy*ay - uz*az)/(ux*ux + uy*uy + uz*uz)   
    tx = ax + k * ux 
    ty = ay + k * uy
    tz = az + k * uz
    T = App.Vector(tx, ty, tz)
    vx, vy, vz = tx - cx, ty - cy, tz - cz
    V = App.Vector(vx, vy, vz)
    distance = math.sqrt(V.dot(V))
    Tprime = T + V
    if info == 1:
        print_point(T, msg=u"Intersection Point at distance of " +
                    str(distance).encode('utf-8') + u" is : ")
    return T, distance, Tprime

def angleBetween(e1, e2):
    """ Return the angle (in degrees) between 2 edges.
    """
    if isinstance(e1,Part.Edge) and isinstance(e2,Part.Edge):
        # Create the Vector for first edge
        v1 = e1.Vertexes[-1].Point
        v2 = e1.Vertexes[0].Point
        ve1 = v1.sub(v2)
        # Create the Vector for second edge
        v3 = e2.Vertexes[-1].Point
        v4 = e2.Vertexes[0].Point
        ve2 = v3.sub(v4)
    elif isinstance(e1,Base.Vector) and isinstance(e2,Base.Vector):
        ve1 = e1
        ve2 = e2
    elif isinstance(e1,Part.Edge) and isinstance(e2,Base.Vector):
        v1 = e1.Vertexes[-1].Point
        v2 = e1.Vertexes[0].Point
        ve1 = v1.sub(v2)
        ve2 = e2
    elif isinstance(e1,Base.Vector) and  isinstance(e2,Part.Edge):
        ve1 = e1
        v3 = e2.Vertexes[-1].Point
        v4 = e2.Vertexes[0].Point
        ve2 = v3.sub(v4)   
    else:
        return
    
    angle = ve1.getAngle(ve2)
    import math
    return math.degrees(angle), angle


#
#Catalogues profilés
#

def ProfIPE():

    dimIPE=[]
    #,,G,h,b,tw,tf,r,A,hi,d,Ø,pmin,pmax,AL,AG,Iy,Wel.y,Wpl.y,iy,Avz,Iz,Wel.z,Wpl.z, iz,Ss,It,Iw,
    #,,kg/m, mm,mm,mm,mm,mm,mm2,mm,mm,,mm,mm,m2/m, m2/t,mm4 ,mm3,mm3,mm,mm2,mm4 ,mm3,mm3,mm,mm,mm4 ,mm6,
    #,,,,,,,,x102,,,,,,,,x104,x103,x103,x10,x102,x104,x103,x103,x10,,x104,x109,
    dimIPE.append(["IPE AA 80",4.9,78,46,3.2,4.2,5,6.31,69.6,59.6,"-","-","-",0.325,65.62,64.1,16.4,18.9,3.19,3,6.85,2.98,4.7,1.04,17.5,0.4,0.09])
    dimIPE.append(["IPE A 80",5,78,46,3.3,4.2,5,6.38,69.6,59.6,"-","-","-",0.325,64.9,64.4,16.5,19,3.18,3.07,6.85,2.98,4.7,1.04,17.6,0.42,0.09])
    dimIPE.append(["IPE 80",6,80,46,3.8,5.2,5,7.64,69.6,59.6,"-","-","-",0.328,54.64,80.1,20,23.2,3.24,3.58,8.49,3.69,5.8,1.05,20.1,0.7,0.12])
    dimIPE.append(["IPE AA 100",6.7,97.6,55,3.6,4.5,7,8.56,88.6,74.6,"-","-","-",0.396,58.93,136,27.9,31.9,3.98,4.4,12.6,4.57,7.2,1.21,20.8,0.73,0.27])
    dimIPE.append(["IPE A 100",6.9,98,55,3.6,4.7,7,8.78,88.6,74.6,"-","-","-",0.397,57.57,141,28.8,33,4.01,4.44,13.1,4.77,7.5,1.22,21.2,0.77,0.28])
    dimIPE.append(["IPE 100",8.1,100,55,4.1,5.7,7,10.3,88.6,74.6,"-","-","-",0.4,49.33,171,34.2,39.4,4.07,5.08,15.9,5.79,9.2,1.24,23.7,1.2,0.35])
    dimIPE.append(["IPE AA 120",8.4,117,64,3.8,4.8,7,10.7,107.4,93.4,"-","-","-",0.47,56.26,244,41.7,47.6,4.79,5.36,21.1,6.59,10.4,1.41,21.6,0.95,0.66])
    dimIPE.append(["IPE A 120",8.7,117.6,64,3.8,5.1,7,11,107.4,93.4,"-","-","-",0.472,54.47,257,43.8,49.9,4.83,5.41,22.4,7,11,1.42,22.2,1.04,0.71])
    dimIPE.append(["IPE 120",10.4,120,64,4.4,6.3,7,13.2,107.4,93.4,"-","-","-",0.475,45.82,318,53,60.7,4.9,6.31,27.7,8.65,13.6,1.45,25.2,1.74,0.89])
    dimIPE.append(["IPE AA 140",10.1,136.6,73,3.8,5.2,7,12.8,126.2,112.2,"-","-","-",0.546,54.26,407,59.7,67.6,5.64,6.14,33.8,9.27,14.5,1.63,22.4,1.19,1.46])
    dimIPE.append(["IPE A 140",10.5,137.4,73,3.8,5.6,7,13.4,126.2,112.2,"-","-","-",0.547,52.05,435,63.3,71.6,5.7,6.21,36.4,10,15.5,1.65,23.2,1.36,1.58])
    dimIPE.append(["IPE 140",12.9,140,73,4.7,6.9,7,16.4,126.2,112.2,"-","-","-",0.551,42.7,541,77.3,88.3,5.74,7.64,44.9,12.3,19.3,1.65,26.7,2.45,1.98])
    dimIPE.append(["IPE AA 160",12.3,156.4,82,4,5.6,9,15.69,145.2,131.2,"-","-","-",0.617,50.13,659,84.3,95.2,6.48,7.74,51.7,12.6,19.7,1.81,25.7,1.81,2.93])
    dimIPE.append(["IPE A 160",12.7,157,82,4,5.9,9,16.2,145.2,127.2,"-","-","-",0.619,48.7,689,87.8,99.1,6.53,7.8,54.4,13.3,20.7,1.83,26.3,1.96,3.09])
    dimIPE.append(["IPE 160",15.8,160,82,5,7.4,9,20.1,145.2,127.2,"-","-","-",0.623,39.47,869,109,124,6.58,9.66,68.3,16.7,26.1,1.84,30.3,3.6,3.96])
    dimIPE.append(["IPE AA 180",14.9,176.4,91,4.3,6.2,9,19,164,146,"M10",48,48,0.693,46.37,1020,116,131,7.32,9.13,78.1,17.2,26.7,2.03,27.2,2.48,5.64])
    dimIPE.append(["IPE A 180",15.4,177,91,4.3,6.5,9,19.6,164,146,"M10",48,48,0.694,45.15,1063,120,135,7.37,9.2,81.9,18,28,2.05,27.8,2.7,5.93])
    dimIPE.append(["IPE 180",18.8,180,91,5.3,8,9,23.9,164,146,"M10",48,48,0.698,37.13,1317,146,166,7.42,11.3,101,22.2,34.6,2.05,31.8,4.79,7.43])
    dimIPE.append(["IPE O 180",21.3,182,92,6,9,9,27.1,164,146,"M10",50,50,0.705,33.12,1505,165,189,7.45,12.7,117,25.5,39.9,2.08,34.5,6.76,8.74])
    dimIPE.append(["IPE AA 200",18,196.4,100,4.5,6.7,12,22.9,183,159,"M10",54,58,0.763,42.51,1533,156,176,8.19,11.4,112,22.4,35,2.21,32,3.84,10.1])
    dimIPE.append(["IPE A 200",18.4,197,100,4.5,7,12,23.5,183,159,"M10",54,58,0.764,41.49,1591,162,182,8.23,11.5,117,23.4,36.5,2.23,32.6,4.11,10.5])
    dimIPE.append(["IPE 200",22.4,200,100,5.6,8.5,12,28.5,183,159,"M10",54,58,0.768,34.36,1943,194,221,8.26,14,142,28.5,44.6,2.24,36.7,6.98,13])
    dimIPE.append(["IPE O 200",25.1,202,102,6.2,9.5,12,32,183,159,"M10",56,60,0.779,31.05,2211,219,249,8.32,15.5,169,33.1,51.9,2.3,39.3,9.45,15.6])
    dimIPE.append(["IPE AA 220",21.2,216.4,110,4.7,7.4,12,27,201.6,177.6,"M12",60,62,0.843,39.78,2219,205,230,9.07,12.8,165,29.9,46.5,2.47,33.6,5.02,17.9])
    dimIPE.append(["IPE A 220",22.2,217,110,5,7.7,12,28.3,201.6,177.6,"M12",60,62,0.843,38.02,2317,214,240,9.05,13.6,171,31.2,48.5,2.46,34.5,5.69,18.7])
    dimIPE.append(["IPE 220",26.2,220,110,5.9,9.2,12,33.4,201.6,177.6,"M12",60,62,0.848,32.36,2772,252,285,9.11,15.9,205,37.3,58.1,2.48,38.4,9.07,22.7])
    dimIPE.append(["IPE O 220",29.4,222,112,6.6,10.2,12,37.4,201.6,177.6,"M10",58,66,0.858,29.24,3134,282,321,9.16,17.7,240,42.8,66.9,2.53,41.1,12.3,26.8])
    dimIPE.append(["IPE AA 240",24.9,236.4,120,4.8,8,15,31.7,220.4,190.4,"M12",64,68,0.917,36.86,3154,267,298,9.97,15.3,231,38.6,60,2.7,38.4,7.33,30.1])
    dimIPE.append(["IPE A 240",26.2,237,120,5.2,8.3,15,33.3,220.4,190.4,"M12",64,68,0.918,35.1,3290,278,312,9.94,16.3,240,40,62.4,2.68,39.4,8.35,31.3])
    dimIPE.append(["IPE 240",30.7,240,120,6.2,9.8,15,39.1,220.4,190.4,"M12",66,68,0.922,30.02,3892,324,367,9.97,19.1,284,47.3,73.9,2.69,43.4,12.9,37.4])
    dimIPE.append(["IPE O 240",34.3,242,122,7,10.8,15,43.7,220.4,190.4,"M12",66,70,0.932,27.17,4369,361,410,10,21.4,329,53.9,84.4,2.74,46.2,17.2,43.7])
    dimIPE.append(["IPE A 270",30.7,267,135,5.5,8.7,15,39.2,249.6,219.6,"M16",70,72,1.037,33.75,4917,368,413,11.2,18.8,358,53,82.3,3.02,40.5,10.3,59.5])
    dimIPE.append(["IPE 270",36.1,270,135,6.6,10.2,15,45.9,249.6,219.6,"M16",72,72,1.041,28.86,5790,429,484,11.2,22.1,420,62.2,97,3.02,44.6,15.9,70.6])
    dimIPE.append(["IPE O 270",42.3,274,136,7.5,12.2,15,53.8,249.6,219.6,"M16",72,72,1.051,24.88,6947,507,575,11.4,25.2,514,75.5,118,3.09,49.5,24.9,87.6])
    dimIPE.append(["IPE A 300",36.5,297,150,6.1,9.2,15,46.5,278.6,248.6,"M16",72,86,1.156,31.65,7173,483,542,12.4,22.3,519,69.2,107,3.34,42.1,13.4,107])
    dimIPE.append(["IPE 300",42.2,300,150,7.1,10.7,15,53.8,278.6,248.6,"M16",72,86,1.16,27.46,8356,557,628,12.5,25.7,604,80.5,125,3.35,46.1,20.1,126])
    dimIPE.append(["IPE O 300",49.3,304,152,8,12.7,15,62.8,278.6,248.6,"M16",74,88,1.174,23.81,9994,658,744,12.6,29.1,746,98.1,153,3.45,51,31.1,158])
    dimIPE.append(["IPE A 330",43,327,160,6.5,10,18,54.7,307,271,"M16",78,96,1.25,29.09,10230,626,702,13.7,27,685,85.6,133,3.54,47.6,19.6,172])
    dimIPE.append(["IPE 330",49.1,330,160,7.5,11.5,18,62.6,307,271,"M16",78,96,1.254,25.52,11770,713,804,13.7,30.8,788,98.5,154,3.55,51.6,28.2,199])
    dimIPE.append(["IPE O 330",57,334,162,8.5,13.5,18,72.6,307,271,"M16",80,98,1.268,22.24,13910,833,943,13.8,34.9,960,119,185,3.64,56.6,42.2,246])
    dimIPE.append(["IPE A 360",50.2,357.6,170,6.6,11.5,18,64,334.6,298.6,"M22",86,88,1.351,26.91,14520,812,907,15.1,29.8,944,111,172,3.84,50.7,26.5,282])
    dimIPE.append(["IPE 360",57.1,360,170,8,12.7,18,72.7,334.6,298.6,"M22",88,88,1.353,23.7,16270,904,1019,15,35.1,1043,123,191,3.79,54.5,37.3,314])
    dimIPE.append(["IPE O 360",66,364,172,9.2,14.7,18,84.1,334.6,298.6,"M22",90,90,1.367,20.69,19050,1047,1186,15.1,40.2,1251,146,227,3.86,59.7,55.8,380])
    dimIPE.append(["IPE A 400",57.4,397,180,7,12,21,73.1,373,331,"M22",94,98,1.464,25.51,20290,1022,1144,16.7,35.8,1171,130,202,4,55.6,34.8,432])
    dimIPE.append(["IPE 400",66.3,400,180,8.6,13.5,21,84.5,373,331,"M22",96,98,1.467,22.12,23130,1160,1307,16.6,42.7,1318,146,229,3.95,60.2,51.1,490])
    dimIPE.append(["IPE O 400",75.7,404,182,9.7,15.5,21,96.4,373,331,"M22",96,100,1.481,19.57,26750,1324,1502,16.7,48,1564,172,269,4.03,65.3,73.1,588])
    dimIPE.append(["IPE A 450",67.2,447,190,7.6,13.1,21,85.6,420.8,378.8,"M24",100,102,1.603,23.87,29760,1331,1494,18.7,42.3,1502,158,246,4.19,58.4,45.7,705])
    dimIPE.append(["IPE 450",77.6,450,190,9.4,14.6,21,98.8,420.8,378.8,"M24",100,102,1.605,20.69,33740,1500,1702,18.5,50.9,1676,176,276,4.12,63.2,66.9,791])
    dimIPE.append(["IPE O 450",92.4,456,192,11,17.6,21,118,420.8,378.8,"M24",102,104,1.622,17.56,40920,1795,2046,18.7,59.4,2085,217,341,4.21,70.8,109,998])
    dimIPE.append(["IPE A 500",79.4,497,200,8.4,14.5,21,101,468,426,"M24",100,112,1.741,21.94,42930,1728,1946,20.6,50.4,1939,194,302,4.38,62,62.8,1125])
    dimIPE.append(["IPE 500",90.7,500,200,10.2,16,21,116,468,426,"M24",102,112,1.744,19.23,48200,1930,2194,20.4,59.9,2142,214,336,4.31,66.8,89.3,1249])
    dimIPE.append(["IPE O 500",107,506,202,12,19,21,137,468,426,"M24",104,114,1.76,16.4,57780,2284,2613,20.6,70.2,2622,260,409,4.38,74.6,144,1548])
    dimIPE.append(["IPE A 550",92.1,547,210,9,15.7,24,117,515.6,467.6,"M24",106,122,1.875,20.36,59980,2193,2475,22.6,60.3,2432,232,362,4.55,68.5,86.5,1710])
    dimIPE.append(["IPE 550",106,550,210,11.1,17.2,24,134,515.6,467.6,"M24",110,122,1.877,17.78,67120,2440,2787,22.4,72.3,2668,254,401,4.45,73.6,123,1884])
    dimIPE.append(["IPE O 550",123,556,212,12.7,20.2,24,156,515.6,467.6,"M24",110,122,1.893,15.45,79160,2847,3263,22.5,82.7,3224,304,481,4.55,81.2,188,2302])
    dimIPE.append(["IPE A 600",108,597,220,9.8,17.5,24,137,562,514,"M27",114,118,2.013,18.72,82920,2778,3141,24.6,70.1,3116,283,442,4.77,72.9,119,2607])
    dimIPE.append(["IPE 600",122,600,220,12,19,24,156,562,514,"M27",116,118,2.015,16.45,92080,3070,3512,24.3,83.8,3387,308,486,4.66,78.1,165,2846])
    dimIPE.append(["IPE O 600",154,610,224,15,24,24,197,562,514,"M27",118,122,2.045,13.24,118300,3879,4471,24.5,104,4521,404,640,4.79,91.1,318,3860])
    dimIPE.append(["IPE 750 x 134",134,750,264,12,15.5,17,171,719,685,"M27",102,158,2.505,18.71,150700,4018,4644,29.7,95.6,4788,362,570,5.3,62.3,122,6440])
    dimIPE.append(["IPE 750 x 147",147,753,265,13.2,17,17,188,719,685,"M27",104,164,2.51,17.06,166100,4411,5110,29.8,105,5289,399,631,5.31,67.1,162,7141])
    dimIPE.append(["IPE 750 x 173",173,762,267,14.4,21.6,17,221,719,685,"M27",104,166,2.534,14.58,205800,5402,6218,30.5,116,6873,515,810,5.57,77.5,274,9391])
    dimIPE.append(["IPE 750 x 196",196,770,268,15.6,25.4,17,251,719,685,"M27",106,166,2.552,12.96,240300,6241,7174,31,127,8175,610,959,5.71,86.3,409,11290])
    dimIPE.append(["IPE 750 x 220",220,779,266,16.5,30,17,280.7,719.1,685.1,"M27",106,164,2.56,11.62,278200,7143,8198,31.48,136.3,9440,709.9,1113,5.8,96.42,609,13200])
    
    return dimIPE

def ProfHE():
    
    dimHE=[]
    #,,G,h,b,tw,tf,r,A,hi,d,Ø,pmin,pmax,AL,AG,Iy,Wel.y,Wpl.y,iy,Avz,Iz,Wel.z,Wpl.z, iz,Ss,It,Iw,
    #,,kg/m, mm,mm,mm,mm,mm,mm2,mm,mm,,mm,mm,m2/m, m2/t,mm4 ,mm3,mm3,mm,mm2,mm4 ,mm3,mm3,mm,mm,mm4 ,mm6,
    #,,,,,,,,x102,,,,,,,,x104,x103,x103,x10,x102,x104,x103,x103,x10,,x104,x109,
    dimHE.append(["HE 100 AA",12.2,91,100,4.2,5.5,12,15.6,80,56,"M10",54,58,0.553,45.17,236.5,51.98,58.36,3.89,6.15,92.06,18.41,28.44,2.43,29.26,2.51,1.68])
    dimHE.append(["HE 100 A",16.7,96,100,5,8,12,21.2,80,56,"M10",54,58,0.561,33.68,349.2,72.76,83.01,4.06,7.56,133.8,26.76,41.14,2.51,35.06,5.24,2.58])
    dimHE.append(["HE 100 B",20.4,100,100,6,10,12,26,80,56,"M10",56,58,0.567,27.76,449.5,89.91,104.2,4.16,9.04,167.3,33.45,51.42,2.53,40.06,9.25,3.38])
    dimHE.append(["HE 100 M",41.8,120,106,12,20,12,53.2,80,56,"M10",62,64,0.619,14.82,1143,190.4,235.8,4.63,18.04,399.2,75.31,116.3,2.74,66.06,68.21,9.93])
    dimHE.append(["HE 120 AA",14.6,109,120,4.2,5.5,12,18.6,98,74,"M12",58,68,0.669,45.94,413.4,75.85,84.12,4.72,6.9,158.8,26.47,40.62,2.93,29.26,2.78,4.24])
    dimHE.append(["HE 120 A",19.9,114,120,5,8,12,25.3,98,74,"M12",58,68,0.677,34.06,606.2,106.3,119.5,4.89,8.46,230.9,38.48,58.85,3.02,35.06,5.99,6.47])
    dimHE.append(["HE 120 B",26.7,120,120,6.5,11,12,34,98,74,"M12",60,68,0.686,25.71,864.4,144.1,165.2,5.04,10.96,317.5,52.92,80.97,3.06,42.56,13.84,9.41])
    dimHE.append(["HE 120 M",52.1,140,126,12.5,21,12,66.4,98,74,"M12",66,74,0.738,14.16,2018,288.2,350.6,5.51,21.15,702.8,111.6,171.6,3.25,68.56,91.66,24.79])
    dimHE.append(["HE 140 AA",18.1,128,140,4.3,6,12,23,116,92,"M16",64,76,0.787,43.53,719.5,112.4,123.8,5.59,7.92,274.8,39.26,59.93,3.45,30.36,3.54,10.21])
    dimHE.append(["HE 140 A",24.7,133,140,5.5,8.5,12,31.4,116,92,"M16",64,76,0.794,32.21,1033,155.4,173.5,5.73,10.12,389.3,55.62,84.85,3.52,36.56,8.13,15.06])
    dimHE.append(["HE 140 B",33.7,140,140,7,12,12,43,116,92,"M16",66,76,0.805,23.88,1509,215.6,245.4,5.93,13.08,549.7,78.52,119.8,3.58,45.06,20.06,22.48])
    dimHE.append(["HE 140 M",63.2,160,146,13,22,12,80.6,116,92,"M16",72,82,0.857,13.56,3291,411.4,493.8,6.39,24.46,1144,156.8,240.5,3.77,71.06,120,54.33])
    dimHE.append(["HE 160 AA",23.8,148,160,4.5,7,15,30.4,134,104,"M20",76,84,0.901,37.81,1283,173.4,190.4,6.5,10.38,478.7,59.84,91.36,3.97,36.07,6.33,23.75])
    dimHE.append(["HE 160 A",30.4,152,160,6,9,15,38.8,134,104,"M20",78,84,0.906,29.78,1673,220.1,245.1,6.57,13.21,615.6,76.95,117.6,3.98,41.57,12.19,31.41])
    dimHE.append(["HE 160 B",42.6,160,160,8,13,15,54.3,134,104,"M20",80,84,0.918,21.56,2492,311.5,354,6.78,17.59,889.2,111.2,170,4.05,51.57,31.24,47.94])
    dimHE.append(["HE 160 M",76.2,180,166,14,23,15,97.1,134,104,"M20",86,90,0.97,12.74,5098,566.5,674.6,7.25,30.81,1759,211.9,325.5,4.26,77.57,162.4,108.1])
    dimHE.append(["HE 180 AA",28.7,167,180,5,7.5,15,36.5,152,122,"M24",84,92,1.018,35.51,1967,235.6,258.2,7.34,12.16,730,81.11,123.6,4.47,37.57,8.33,46.36])
    dimHE.append(["HE 180 A",35.5,171,180,6,9.5,15,45.3,152,122,"M24",86,92,1.024,28.83,2510,293.6,324.9,7.45,14.47,924.6,102.7,156.5,4.52,42.57,14.8,60.21])
    dimHE.append(["HE 180 B",51.2,180,180,8.5,14,15,65.3,152,122,"M24",88,92,1.037,20.25,3831,425.7,481.4,7.66,20.24,1363,151.4,231,4.57,54.07,42.16,93.75])
    dimHE.append(["HE 180 M",88.9,200,186,14.5,24,15,113.3,152,122,"M24",94,98,1.089,12.25,7483,748.3,883.4,8.13,34.65,2580,277.4,425.2,4.77,80.07,203.3,199.3])
    dimHE.append(["HE 200 AA",34.6,186,200,5.5,8,18,44.1,170,134,"M27",96,100,1.13,32.62,2944,316.6,347.1,8.17,15.45,1068,106.8,163.2,4.92,42.59,12.69,84.49])
    dimHE.append(["HE 200 A",42.3,190,200,6.5,10,18,53.8,170,134,"M27",98,100,1.136,26.89,3692,388.6,429.5,8.28,18.08,1336,133.6,203.8,4.98,47.59,20.98,108])
    dimHE.append(["HE 200 B",61.3,200,200,9,15,18,78.1,170,134,"M27",100,100,1.151,18.78,5696,569.6,642.5,8.54,24.83,2003,200.3,305.8,5.07,60.09,59.28,171.1])
    dimHE.append(["HE 200 M",103,220,206,15,25,18,131.3,170,134,"M27",106,106,1.203,11.67,10640,967.4,1135,9,41.03,3651,354.5,543.2,5.27,86.09,259.4,346.3])
    dimHE.append(["HE 220 AA",40.4,205,220,6,8.5,18,51.5,188,152,"M27",98,118,1.247,30.87,4170,406.9,445.5,9,17.63,1510,137.3,209.3,5.42,44.09,15.93,145.6])
    dimHE.append(["HE 220 A",50.5,210,220,7,11,18,64.3,188,152,"M27",98,118,1.255,24.85,5410,515.2,568.5,9.17,20.67,1955,177.7,270.6,5.51,50.09,28.46,193.3])
    dimHE.append(["HE 220 B",71.5,220,220,9.5,16,18,91,188,152,"M27",100,118,1.27,17.77,8091,735.5,827,9.43,27.92,2843,258.5,393.9,5.59,62.59,76.57,295.4])
    dimHE.append(["HE 220 M",117,240,226,15.5,26,18,149.4,188,152,"M27",108,124,1.322,11.27,14600,1217,1419,9.89,45.31,5012,443.5,678.6,5.79,88.59,315.3,572.7])
    dimHE.append(["HE 240 AA",47.4,224,240,6.5,9,21,60.4,206,164,"M27",104,138,1.359,28.67,5835,521,570.6,9.83,21.54,2077,173.1,264.4,5.87,49.1,22.98,239.6])
    dimHE.append(["HE 240 A",60.3,230,240,7.5,12,21,76.8,206,164,"M27",104,138,1.369,22.7,7763,675.1,744.6,10.05,25.18,2769,230.7,351.7,6,56.1,41.55,328.5])
    dimHE.append(["HE 240 B",83.2,240,240,10,17,21,106,206,164,"M27",108,138,1.384,16.63,11260,938.3,1053,10.31,33.23,3923,326.9,498.4,6.08,68.6,102.7,486.9])
    dimHE.append(["HE 240 M",157,270,248,18,32,21,199.6,206,164,"M27",116,146,1.46,9.32,24290,1799,2117,11.03,60.07,8153,657.5,1006,6.39,106.6,627.9,1152])
    dimHE.append(["HE 260 AA",54.1,244,260,6.5,9.5,24,69,225,177,"M27",110,158,1.474,27.22,7981,654.1,714.5,10.76,24.75,2788,214.5,327.7,6.36,53.62,30.31,382.6])
    dimHE.append(["HE 260 A",68.2,250,260,7.5,12.5,24,86.8,225,177,"M27",110,158,1.484,21.77,10450,836.4,919.8,10.97,28.76,3668,282.1,430.2,6.5,60.62,52.37,516.4])
    dimHE.append(["HE 260 B",93,260,260,10,17.5,24,118.4,225,177,"M27",114,158,1.499,16.12,14920,1148,1283,11.22,37.59,5135,395,602.2,6.58,73.12,123.8,753.7])
    dimHE.append(["HE 260 M",172,290,268,18,32.5,24,219.6,225,177,"M27",122,166,1.575,9.13,31310,2159,2524,11.94,66.89,10450,779.7,1192,6.9,111.1,719,1728])
    dimHE.append(["HE 280 AA",61.2,264,280,7,10,24,78,244,196,"M27",110,178,1.593,26.01,10560,799.8,873.1,11.63,27.52,3664,261.7,399.4,6.85,55.12,36.22,590.1])
    dimHE.append(["HE 280 A",76.4,270,280,8,13,24,97.3,244,196,"M27",112,178,1.603,20.99,13670,1013,1112,11.86,31.74,4763,340.2,518.1,7,62.12,62.1,785.4])
    dimHE.append(["HE 280 B",103,280,280,10.5,18,24,131.4,244,196,"M27",114,178,1.618,15.69,19270,1376,1534,12.11,41.09,6595,471,717.6,7.09,74.62,143.7,1130])
    dimHE.append(["HE 280 M",189,310,288,18.5,33,24,240.2,244,196,"M27",122,186,1.694,8.98,39550,2551,2966,12.83,72.03,13160,914.1,1397,7.4,112.6,807.3,2520])
    dimHE.append(["HE 300 AA",69.8,283,300,7.5,10.5,27,88.9,262,208,"M27",116,198,1.705,24.42,13800,975.6,1065,12.46,32.37,4734,315.6,482.3,7.3,60.13,49.35,877.2])
    dimHE.append(["HE 300 A",88.3,290,300,8.5,14,27,112.5,262,208,"M27",118,198,1.717,19.43,18260,1260,1383,12.74,37.28,6310,420.6,641.2,7.49,68.13,85.17,1200])
    dimHE.append(["HE 300 B",117,300,300,11,19,27,149.1,262,208,"M27",120,198,1.732,14.8,25170,1678,1869,12.99,47.43,8563,570.9,870.1,7.58,80.63,185,1688])
    dimHE.append(["HE 300 M",238,340,310,21,39,27,303.1,262,208,"M27",132,208,1.832,7.7,59200,3482,4078,13.98,90.53,19400,1252,1913,8,130.6,1408,4386])
    dimHE.append(["HE 320 AA",74.2,301,300,8,11,27,94.6,279,225,"M27",118,198,1.74,23.43,16450,1093,1196,13.19,35.4,4959,330.6,505.7,7.24,61.63,55.87,1041])
    dimHE.append(["HE 320 A",97.6,310,300,9,15.5,27,124.4,279,225,"M27",118,198,1.756,17.98,22930,1479,1628,13.58,41.13,6985,465.7,709.7,7.49,71.63,108,1512])
    dimHE.append(["HE 320 B",127,320,300,11.5,20.5,27,161.3,279,225,"M27",122,198,1.771,13.98,30820,1926,2149,13.82,51.77,9239,615.9,939.1,7.57,84.13,225.1,2069])
    dimHE.append(["HE 320 M",245,359,309,21,40,27,312,279,225,"M27",132,204,1.866,7.62,68130,3796,4435,14.78,94.85,19710,1276,1951,7.95,132.6,1501,5004])
    dimHE.append(["HE 340 AA",78.9,320,300,8.5,11.5,27,100.5,297,243,"M27",118,198,1.777,22.52,19550,1222,1341,13.95,38.69,5185,345.6,529.3,7.18,63.13,63.07,1231])
    dimHE.append(["HE 340 A",105,330,300,9.5,16.5,27,133.5,297,243,"M27",118,198,1.795,17.13,27690,1678,1850,14.4,44.95,7436,495.7,755.9,7.46,74.13,127.2,1824])
    dimHE.append(["HE 340 B",134,340,300,12,21.5,27,170.9,297,243,"M27",122,198,1.81,13.49,36660,2156,2408,14.65,56.09,9690,646,985.7,7.53,86.63,257.2,2454])
    dimHE.append(["HE 340 M",248,377,309,21,40,27,315.8,297,243,"M27",132,204,1.902,7.67,76370,4052,4718,15.55,98.63,19710,1276,1953,7.9,132.6,1506,5584])
    dimHE.append(["HE 360 AA",83.7,339,300,9,12,27,106.6,315,261,"M27",118,198,1.814,21.67,23040,1359,1495,14.7,42.17,5410,360.7,553,7.12,64.63,70.99,1444])
    dimHE.append(["HE 360 A",112,350,300,10,17.5,27,142.8,315,261,"M27",120,198,1.834,16.36,33090,1891,2088,15.22,48.96,7887,525.8,802.3,7.43,76.63,148.8,2177])
    dimHE.append(["HE 360 B",142,360,300,12.5,22.5,27,180.6,315,261,"M27",122,198,1.849,13.04,43190,2400,2683,15.46,60.6,10140,676.1,1032,7.49,89.13,292.5,2883])
    dimHE.append(["HE 360 M",250,395,308,21,40,27,318.8,315,261,"M27",132,204,1.934,7.73,84870,4297,4989,16.32,102.4,19520,1268,1942,7.83,132.6,1507,6137])
    dimHE.append(["HE 400 AA",92.4,378,300,9.5,13,27,117.7,352,298,"M27",118,198,1.891,20.46,31250,1654,1824,16.3,47.95,5861,390.8,599.7,7.06,67.13,84.69,1948])
    dimHE.append(["HE 400 A",125,390,300,11,19,27,159,352,298,"M27",120,198,1.912,15.32,45070,2311,2562,16.84,57.33,8564,570.9,872.9,7.34,80.63,189,2942])
    dimHE.append(["HE 400 B",155,400,300,13.5,24,27,197.8,352,298,"M27",124,198,1.927,12.41,57680,2884,3232,17.08,69.98,10820,721.3,1104,7.4,93.13,355.7,3817])
    dimHE.append(["HE 400 M",256,432,307,21,40,27,325.8,352,298,"M27",132,202,2.004,7.84,104100,4820,5571,17.88,110.2,19340,1260,1934,7.7,132.6,1515,7410])
    dimHE.append(["HE 450 AA",99.7,425,300,10,13.5,27,127.1,398,344,"M27",120,198,1.984,19.89,41890,1971,2183,18.16,54.7,6088,405.8,624.4,6.92,68.63,95.61,2572])
    dimHE.append(["HE 450 A",140,440,300,11.5,21,27,178,398,344,"M27",122,198,2.011,14.39,63720,2896,3216,18.92,65.78,9465,631,965.5,7.29,85.13,243.8,4148])
    dimHE.append(["HE 450 B",171,450,300,14,26,27,218,398,344,"M27",124,198,2.026,11.84,79890,3551,3982,19.14,79.66,11720,781.4,1198,7.33,97.63,440.5,5258])
    dimHE.append(["HE 450 M",263,478,307,21,40,27,335.4,398,344,"M27",132,202,2.096,7.96,131500,5501,6331,19.8,119.8,19340,1260,1939,7.59,132.6,1529,9251])
    dimHE.append(["HE 500 AA",107,472,300,10.5,14,27,136.9,444,390,"M27",120,198,2.077,19.33,54640,2315,2576,19.98,61.91,6314,420.9,649.3,6.79,70.13,107.7,3304])
    dimHE.append(["HE 500 A",155,490,300,12,23,27,197.5,444,390,"M27",122,198,2.11,13.6,86970,3550,3949,20.98,74.72,10370,691.1,1059,7.24,89.63,309.3,5643])
    dimHE.append(["HE 500 B",187,500,300,14.5,28,27,238.6,444,390,"M27",124,198,2.125,11.34,107200,4287,4815,21.19,89.82,12620,841.6,1292,7.27,102.1,538.4,7018])
    dimHE.append(["HE 500 M",270,524,306,21,40,27,344.3,444,390,"M27",132,202,2.184,8.08,161900,6180,7094,21.69,129.5,19150,1252,1932,7.46,132.6,1539,11190])
    dimHE.append(["HE 550 AA",120,522,300,11.5,15,27,152.8,492,438,"M27",122,198,2.175,18.13,72870,2792,3128,21.84,72.66,6767,451.1,698.6,6.65,73.13,133.7,4338])
    dimHE.append(["HE 550 A",166,540,300,12.5,24,27,211.8,492,438,"M27",122,198,2.209,13.29,111900,4146,4622,22.99,83.72,10820,721.3,1107,7.15,92.13,351.5,7189])
    dimHE.append(["HE 550 B",199,550,300,15,29,27,254.1,492,438,"M27",124,198,2.224,11.15,136700,4971,5591,23.2,100.1,13080,871.8,1341,7.17,104.6,600.3,8856])
    dimHE.append(["HE 550 M",278,572,306,21,40,27,354.4,492,438,"M27",132,202,2.28,8.2,198000,6923,7933,23.64,139.6,19160,1252,1937,7.35,132.6,1554,13520])
    dimHE.append(["HE 600 AA",129,571,300,12,15.5,27,164.1,540,486,"M27",122,198,2.272,17.64,91900,3218,3623,23.66,81.29,6993,466.2,724.5,6.53,74.63,149.8,5381])
    dimHE.append(["HE 600 A",178,590,300,13,25,27,226.5,540,486,"M27",122,198,2.308,12.98,141200,4787,5350,24.97,93.21,11270,751.4,1156,7.05,94.63,397.8,8978])
    dimHE.append(["HE 600 B",212,600,300,15.5,30,27,270,540,486,"M27",126,198,2.323,10.96,171000,5701,6425,25.17,110.8,13530,902,1391,7.08,107.1,667.2,10970])
    dimHE.append(["HE 600 M",285,620,305,21,40,27,363.7,540,486,"M27",132,200,2.372,8.31,237400,7660,8772,25.55,149.7,18980,1244,1930,7.22,132.6,1564,15910])
    dimHE.append(["HE 600 x 337",337,632,310,25.5,46,27,429.2,540,486,"M27",138,202,2.407,7.14,283200,8961,10380,25.69,180.5,22940,1480,2310,7.31,149.1,2451,19610])
    dimHE.append(["HE 600 x 399",399,648,315,30,54,27,508.5,540,486,"M27",142,208,2.45,6.14,344600,10640,12460,26.03,213.6,28280,1796,2814,7.46,169.6,3966,24810])
    dimHE.append(["HE 650 AA",138,620,300,12.5,16,27,175.8,588,534,"M27",122,198,2.369,17.17,113900,3676,4160,25.46,90.4,7221,481.4,750.7,6.41,76.13,167.5,6567])
    dimHE.append(["HE 650 A",190,640,300,13.5,26,27,241.6,588,534,"M27",124,198,2.407,12.69,175200,5474,6136,26.93,103.2,11720,781.6,1205,6.97,97.13,448.3,11030])
    dimHE.append(["HE 650 B",225,650,300,16,31,27,286.3,588,534,"M27",126,198,2.422,10.77,210600,6480,7320,27.12,122,13980,932.3,1441,6.99,109.6,739.2,13360])
    dimHE.append(["HE 650 M",293,668,305,21,40,27,373.7,588,534,"M27",132,200,2.468,8.41,281700,8433,9657,27.45,159.7,18980,1245,1936,7.13,132.6,1579,18650])
    dimHE.append(["HE 650 x 343",343,680,309,25,46,27,437.5,588,534,"M27",138,202,2.5,7.28,333700,9815,11350,27.62,189.6,22720,1470,2300,7.21,148.6,2442,22730])
    dimHE.append(["HE 650 x 407",407,696,314,29.5,54,27,518.8,588,534,"M27",142,206,2.543,6.24,405400,11650,13620,27.95,224.8,28020,1785,2803,7.35,169.1,3958,28710])
    dimHE.append(["HE 700 AA",150,670,300,13,17,27,190.9,636,582,"M27",122,198,2.468,16.46,142700,4260,4840,27.34,100.3,7673,511.5,799.7,6.34,78.63,195.2,8155])
    dimHE.append(["HE 700 A",204,690,300,14.5,27,27,260.5,636,582,"M27",124,198,2.505,12.25,215300,6241,7032,28.75,117,12180,811.9,1257,6.84,100.1,513.9,13350])
    dimHE.append(["HE 700 B",241,700,300,17,32,27,306.4,636,582,"M27",126,198,2.52,10.48,256900,7340,8327,28.96,137.1,14440,962.7,1495,6.87,112.6,830.9,16060])
    dimHE.append(["HE 700 M",301,716,304,21,40,27,383,636,582,"M27",132,200,2.56,8.51,329300,9198,10540,29.32,169.8,18800,1240,1929,7.01,132.6,1589,21400])
    dimHE.append(["HE 700 x 352",352,728,308,25,46,27,448.6,636,582,"M27",138,200,2.592,7.36,389700,10710,12390,29.47,201.6,22510,1461,2293,7.08,148.6,2461,26050])
    dimHE.append(["HE 700 x 418",418,744,313,29.5,54,27,531.9,636,582,"M27",142,206,2.635,6.31,472500,12700,14840,29.8,239,27760,1774,2797,7.22,169.1,3989,32850])
    dimHE.append(["HE 800 AA",172,770,300,14,18,30,218.5,734,674,"M27",130,198,2.66,15.51,208900,5426,6225,30.92,123.8,8134,542.2,856.6,6.1,85.15,256.8,11450])
    dimHE.append(["HE 800 A",224,790,300,15,28,30,285.8,734,674,"M27",130,198,2.698,12.03,303400,7682,8699,32.58,138.8,12640,842.6,1312,6.65,106.1,596.9,18290])
    dimHE.append(["HE 800 B",262,800,300,17.5,33,30,334.2,734,674,"M27",134,198,2.713,10.34,359100,8977,10230,32.78,161.8,14900,993.6,1553,6.68,118.6,946,21840])
    dimHE.append(["HE 800 M",317,814,303,21,40,30,404.3,734,674,"M27",138,198,2.746,8.66,442600,10870,12490,33.09,194.3,18630,1230,1930,6.79,136.1,1646,27780])
    dimHE.append(["HE 800 x 373",373,826,308,25,46,30,474.6,734,674,"M27",144,200,2.782,7.47,523900,12690,14700,33.23,230.3,22530,1463,2311,6.89,152.1,2554,34070])
    dimHE.append(["HE 800 x 444",444,842,313,30,54,30,566,734,674,"M27",148,206,2.824,6.36,634500,15070,17640,33.48,276.5,27800,1776,2827,7.01,173.1,4180,42840])
    dimHE.append(["HE 900 AA",198,870,300,15,20,30,252.2,830,770,"M27",130,198,2.858,14.44,301100,6923,7999,34.55,147.2,9041,602.8,957.7,5.99,90.15,334.9,16260])
    dimHE.append(["HE 900 A",252,890,300,16,30,30,320.5,830,770,"M27",132,198,2.896,11.51,422100,9485,10810,36.29,163.3,13550,903.2,1414,6.5,111.1,736.8,24960])
    dimHE.append(["HE 900 B",291,900,300,18.5,35,30,371.3,830,770,"M27",134,198,2.911,9.99,494100,10980,12580,36.48,188.8,15820,1050,1658,6.53,123.6,1137,29460])
    dimHE.append(["HE 900 M",333,910,302,21,40,30,423.6,830,770,"M27",138,198,2.934,8.82,570400,12540,14440,36.7,214.4,18450,1220,1929,6.6,136.1,1671,34750])
    dimHE.append(["HE 900 x 391",391,922,307,25,46,30,497.7,830,770,"M27",144,200,2.97,7.6,674300,14630,16990,36.81,254.3,22320,1454,2312,6.7,152.1,2597,42560])
    dimHE.append(["HE 900 x 466",466,938,312,30,54,30,593.7,830,770,"M27",148,204,3.012,6.46,814900,17380,20380,37.05,305.3,27560,1767,2832,6.81,173.1,4256,53400])
    dimHE.append(["HE 1000 AA",222,970,300,16,21,30,282.2,928,868,"M27",132,198,3.056,13.8,406500,8380,9777,37.95,172.2,9501,633.4,1016,5.8,93.15,403.4,21280])
    dimHE.append(["HE 1000 x 249",249,980,300,16.5,26,30,316.8,928,868,"M27",134,194,3.08,12.37,481100,9818,11350,38.97,180.7,11750,784,1245,6.09,103.6,584.4,26620])
    dimHE.append(["HE 1000 A",272,990,300,16.5,31,30,346.8,928,868,"M27",132,198,3.095,11.37,553800,11190,12820,39.96,184.6,14000,933.6,1470,6.35,113.6,822.4,32070])
    dimHE.append(["HE 1000 B",314,1000,300,19,36,30,400,928,868,"M27",134,198,3.11,9.91,644700,12890,14860,40.15,212.5,16280,1085,1716,6.38,126.1,1254,37640])
    dimHE.append(["HE 1000 M",349,1008,302,21,40,30,444.2,928,868,"M27",138,198,3.13,8.98,722300,14330,16570,40.32,235,18460,1222,1940,6.45,136.1,1701,43020])
    dimHE.append(["HE 1000 x 393",393,1016,303,24.4,43.9,30,500.2,928,868,"M27",142,198,3.14,8.01,807700,15900,18540,40.18,271.3,20500,1353,2168,6.4,147.3,2332,48080])
    dimHE.append(["HE 1000 x 415",415,1020,304,26,46,30,528.7,928,868,"M27",144,198,3.15,7.6,853100,16728,19571,40.17,288.6,21710,1428,2298,6.41,153.1,2713,51080])
    dimHE.append(["HE 1000 x 438",438,1026,305,26.9,49,30,556,928,868,"M27",146,198,3.17,7.25,909200,17720,20750,40.43,299.9,23360,1531,2463,6.48,160,3190,55290])
    dimHE.append(["HE 1000 x 494",494,1036,309,31,54,30,629.1,928,868,"M27",148,204,3.19,6.47,1028000,19845,23413,40.42,344.5,26820,1736,2818,6.53,174.1,4433,64010])
    dimHE.append(["HE 1000 x 584",584,1056,314,36,64,30,743.7,928,868,"M27",154,208,3.24,5.56,1246100,23600,28039,40.93,403.2,33430,2130,3475,6.7,199.1,7230,81240])

    return dimHE

def ProfIPN():
    
    dimIPN=[]
    #,G,h,b,tw,tf,r1,r2,A,d,Ø,pmin,pmax,AL,AG,Iy,Wel.y,Wpl.y,iy,Avz,Iz,Wel.z,Wpl.z, iz,Ss,It,Iw,
    #,kg/m, mm,mm,mm,mm,mm,mm,mm2,mm,,mm,mm,m2/m, m2/t,mm4 ,mm3,mm3,mm,mm2,mm4 ,mm3,mm3,mm,mm,mm4 ,mm6,
    #,,,,,,,,x102,,,,,,,x104,x103,x103,x10,x102,x104,x103,x103,x10,,x104,x109,
    dimIPN.append([5.94,80,42,3.9,5.9,3.9,2.3,7.57,59,"-","-","-",0.304,51.09,77.8,19.5,22.8,3.2,3.41,6.29,3,5,0.91,21.6,0.87,0.09])
    dimIPN.append([8.34,100,50,4.5,6.8,4.5,2.7,10.6,75.7,"-","-","-",0.37,44.47,171,34.2,39.8,4.01,4.85,12.2,4.88,8.1,1.07,25,1.6,0.27])
    dimIPN.append([11.1,120,58,5.1,7.7,5.1,3.1,14.2,92.4,"-","-","-",0.439,39.38,328,54.7,63.6,4.81,6.63,21.5,7.41,12.4,1.23,28.4,2.71,0.69])
    dimIPN.append([14.3,140,66,5.7,8.6,5.7,3.4,18.2,109.1,"-","-","-",0.502,34.94,573,81.9,95.4,5.61,8.65,35.2,10.7,17.9,1.4,31.8,4.32,1.54])
    dimIPN.append([17.9,160,74,6.3,9.5,6.3,3.8,22.8,125.8,"-","-","-",0.575,32.13,935,117,136,6.4,10.83,54.7,14.8,24.9,1.55,35.2,6.57,3.14])
    dimIPN.append([21.9,180,82,6.9,10.4,6.9,4.1,27.9,142.4,"-","-","-",0.64,29.22,1450,161,187,7.2,13.35,81.3,19.8,33.2,1.71,38.6,9.58,5.92])
    dimIPN.append([26.2,200,90,7.5,11.3,7.5,4.5,33.4,159.1,"-","-","-",0.709,27.04,2140,214,250,8,16.03,117,26,43.5,1.87,42,13.5,10.5])
    dimIPN.append([31.1,220,98,8.1,12.2,8.1,4.9,39.5,175.8,"M10",50,56,0.775,24.99,3060,278,324,8.8,19.06,162,33.1,55.7,2.02,45.4,18.6,17.8])
    dimIPN.append([36.2,240,106,8.7,13.1,8.7,5.2,46.1,192.5,"M10",54,60,0.844,23.32,4250,354,412,9.59,22.33,221,41.7,70,2.2,48.9,25,28.7])
    dimIPN.append([41.9,260,113,9.4,14.1,9.4,5.6,53.3,208.9,"M12",62,62,0.906,21.65,5740,442,514,10.4,26.08,288,51,85.9,2.32,52.6,33.5,44.1])
    dimIPN.append([47.9,280,119,10.1,15.2,10.1,6.1,61,225.1,"M12",68,68,0.966,20.17,7590,542,632,11.1,30.18,364,61.2,103,2.45,56.4,44.2,64.6])
    dimIPN.append([54.2,300,125,10.8,16.2,10.8,6.5,69,241.6,"M12",70,74,1.03,19.02,9800,653,762,11.9,34.58,451,72.2,121,2.56,60.1,56.8,91.8])
    dimIPN.append([61,320,131,11.5,17.3,11.5,6.9,77.7,257.9,"M12",70,80,1.09,17.87,12510,782,914,12.7,39.26,555,84.7,143,2.67,63.9,72.5,129])
    dimIPN.append([68,340,137,12.2,18.3,12.2,7.3,86.7,274.3,"M12",78,86,1.15,16.9,15700,923,1080,13.5,44.27,674,98.4,166,2.8,67.6,90.4,176])
    dimIPN.append([76.1,360,143,13,19.5,13,7.8,97,290.2,"M12",78,92,1.21,15.89,19610,1090,1276,14.2,49.95,818,114,194,2.9,71.8,115,240])
    dimIPN.append([84,380,149,13.7,20.5,13.7,8.2,107,306.7,"M16",84,86,1.27,15.12,24010,1260,1482,15,55.55,975,131,221,3.02,75.4,141,319])
    dimIPN.append([92.4,400,155,14.4,21.6,14.4,8.6,118,322.9,"M16",86,92,1.33,14.36,29210,1460,1714,15.7,61.69,1160,149,253,3.13,79.3,170,420])
    dimIPN.append([115,450,170,16.2,24.3,16.2,9.7,147,363.6,"M16",92,106,1.48,12.83,45850,2040,2400,17.7,77.79,1730,203,345,3.43,88.9,267,791])
    dimIPN.append([141,500,185,18,27,18,10.8,179,404.3,"M20",102,110,1.63,11.6,68740,2750,3240,19.6,95.6,2480,268,456,3.72,98.5,402,1400])
    dimIPN.append([166,550,200,19,30,19,11.9,212,445.6,"M22",112,118,1.8,10.8,99180,3610,4240,21.6,111.3,3490,349,592,4.02,107.3,544,2390])
    dimIPN.append([199,600,215,21.6,32.4,21.6,13,254,485.8,"M24",126,128,1.92,9.89,139000,4630,5452,23.4,138,4670,434,752,4.3,117.6,787,3814])

    return dimIPN

def ProfUPN():
    
    dimUPN=[]
    #,G,h,b,tw,tf,r1,r2,A,d,Ø,emin,emax,AL,AG,Iy,Wel.y,Wpl.y,iy,Avz,Iz,Wel.z,Wpl.z, iz,ss,It,Iw,ys,ym,
    #,kg/m, mm,mm,mm,mm,mm,mm,mm2,mm,,mm,mm,m2/m, m2/t,mm4 ,mm3,mm3,mm,mm2,mm4,mm3,mm3,mm,mm,mm4,mm6,mm,mm,
    #,,,,,,,,x102,,,,,,,x104,x103,x103,x10,x102,x104,x103,x103,x10,,x104,x109,x10,x10,
    dimUPN.append([5.59,50,38,5,7,7,3.5,7.12,21,"-","-","-",0.232,42.22,26.4,10.6,13.1,1.92,2.77,9.12,3.75,6.78,1.13,16.7,1.12,0.03,1.37,2.47])
    dimUPN.append([7.09,65,42,5.5,7.5,7.5,4,9.03,34,"-","-","-",0.273,39.57,57.5,17.7,21.7,2.52,3.68,14.1,5.07,9.38,1.25,18,1.61,0.08,1.42,2.6])
    dimUPN.append([8.64,80,45,6,8,8,4,11,47,"-","-","-",0.312,37.1,106,26.5,32.3,3.1,4.9,19.4,6.36,11.9,1.33,19.4,2.2,0.18,1.45,2.67])
    dimUPN.append([10.6,100,50,6,8.5,8.5,4.5,13.5,64,"-","-","-",0.372,35.1,206,41.2,49,3.91,6.46,29.3,8.49,16.2,1.47,20.3,2.81,0.41,1.55,2.93])
    dimUPN.append([13.4,120,55,7,9,9,4.5,17,82,"-","-","-",0.434,32.52,364,60.7,72.6,4.62,8.8,43.2,11.1,21.2,1.59,22.2,4.15,0.9,1.6,3.03])
    dimUPN.append([16,140,60,7,10,10,5,20.4,98,"M12",33,37,0.489,30.54,605,86.4,103,5.45,10.4,62.7,14.8,28.3,1.75,23.9,5.68,1.8,1.75,3.37])
    dimUPN.append([18.8,160,65,7.5,10.5,10.5,5.5,24,115,"M12",34,42,0.546,28.98,925,116,138,6.21,12.6,85.3,18.3,35.2,1.89,25.3,7.39,3.26,1.84,3.56])
    dimUPN.append([22,180,70,8,11,11,5.5,28,133,"M16",38,41,0.611,27.8,1350,150,179,6.95,15.1,114,22.4,42.9,2.02,26.7,9.55,5.57,1.92,3.75])
    dimUPN.append([25.3,200,75,8.5,11.5,11.5,6,32.2,151,"M16",39,46,0.661,26.15,1910,191,228,7.7,17.7,148,27,51.8,2.14,28.1,11.9,9.07,2.01,3.94])
    dimUPN.append([29.4,220,80,9,12.5,12.5,6.5,37.4,167,"M16",40,51,0.718,24.46,2690,245,292,8.48,20.6,197,33.6,64.1,2.3,30.3,16,14.6,2.14,4.2])
    dimUPN.append([33.2,240,85,9.5,13,13,6.5,42.3,184,"M20",46,50,0.775,23.34,3600,300,358,9.22,23.7,248,39.6,75.7,2.42,31.7,19.7,22.1,2.23,4.39])
    dimUPN.append([37.9,260,90,10,14,14,7,48.3,200,"M22",50,52,0.834,22,4820,371,442,9.99,27.1,317,47.7,91.6,2.56,33.9,25.5,33.3,2.36,4.66])
    dimUPN.append([41.8,280,95,10,15,15,7.5,53.3,216,"M22",52,57,0.89,21.27,6280,448,532,10.9,29.3,399,57.2,109,2.74,35.6,31,48.5,2.53,5.02])
    dimUPN.append([46.2,300,100,10,16,16,8,58.8,232,"M24",55,59,0.95,20.58,8030,535,632,11.7,31.8,495,67.8,130,2.9,37.3,37.4,69.1,2.7,5.41])
    dimUPN.append([59.5,320,100,14,17.5,17.5,8.8,75.8,246,"M22",58,62,0.982,16.5,10870,679,826,12.1,47.1,597,80.6,152,2.81,43,66.7,96.1,2.6,4.82])
    dimUPN.append([60.6,350,100,14,16,16,8,77.3,282,"M22",56,62,1.05,17.25,12840,734,918,12.9,50.8,570,75,143,2.72,40.7,61.2,114,2.4,4.45])
    dimUPN.append([63.1,380,102,13.5,16,16,8,80.4,313,"M24",59,60,1.11,17.59,15760,829,1010,14,53.2,615,78.7,148,2.77,40.3,59.1,146,2.38,4.58])
    dimUPN.append([71.8,400,110,14,18,18,9,91.5,324,"M27",61,62,1.18,16.46,20350,1020,1240,14.9,58.6,846,102,190,3.04,44,81.6,221,2.65,5.11])
        
    return dimUPN

def ProfUPE():
    
    dimUPE=[]
    #,G,h,b,tw,tf,r1,r2,A,d,Ø,emin,emax,AL,AG,Iy,Wel.y,Wpl.y,iy,Avz,Iz,Wel.z,Wpl.z, iz,ss,It,Iw,ys,ym
    #,kg/m, mm,mm,mm,mm,mm,mm,mm2,mm,,mm,mm,m2/m, m2/t,mm4 ,mm3,mm3,mm,mm2,mm4,mm3,mm3,mm,mm,mm4,mm6,mm,mm
    #,,,,,,,,x102,,,,,,,x104,x103,x103,x10,x102,x104,x103,x103,x10,,x104,x109,x10,x10
    dimUPE.append([7.9,80,50,4,7,10,10.1,66,46,"-","-","-",0.343,43.45,107,26.8,31.2,3.26,4.05,25.5,8,14.3,1.59,16.9,1.47,0.22,1.82,3.71])
    dimUPE.append([9.82,100,55,4.5,7.5,10,12.5,85,65,"M12",35,36,0.402,41,207,41.4,48,4.07,5.34,38.3,10.6,19.3,1.75,17.9,2.01,0.53,1.91,3.93])
    dimUPE.append([12.1,120,60,5,8,12,15.4,104,80,"M12",35,41,0.46,37.98,364,60.6,70.3,4.86,7.18,55.5,13.8,25.3,1.9,20,2.9,1.12,1.98,4.12])
    dimUPE.append([14.5,140,65,5,9,12,18.4,122,98,"M16",35,38,0.52,35.95,600,85.6,98.8,5.71,8.25,78.8,18.2,33.2,2.07,21,4.05,2.2,2.17,4.54])
    dimUPE.append([17,160,70,5.5,9.5,12,21.7,141,117,"M16",36,43,0.579,34.01,911,114,132,6.48,10,107,22.6,41.5,2.22,22,5.2,3.96,2.27,4.76])
    dimUPE.append([19.7,180,75,5.5,10.5,12,25.1,159,135,"M16",36,48,0.639,32.4,1350,150,173,7.34,11.2,144,28.6,52.3,2.39,23,6.99,6.81,2.47,5.19])
    dimUPE.append([22.8,200,80,6,11,13,29,178,152,"M20",46,47,0.697,30.6,1910,191,220,8.11,13.5,187,34.5,63.3,2.54,24.6,8.89,11,2.56,5.41])
    dimUPE.append([26.6,220,85,6.5,12,13,33.9,196,170,"M22",47,49,0.756,28.43,2680,244,281,8.9,15.8,247,42.5,78.2,2.7,26.1,12.1,17.6,2.7,5.7])
    dimUPE.append([30.2,240,90,7,12.5,15,38.5,215,185,"M24",47,51,0.813,26.89,3600,300,347,9.67,18.8,311,50.1,92.2,2.84,28.3,15.1,26.4,2.79,5.91])
    dimUPE.append([35.2,270,95,7.5,13.5,15,44.8,243,213,"M27",48,50,0.892,25.34,5250,389,451,10.8,22.2,401,60.7,112,2.99,29.8,19.9,43.6,2.89,6.14])
    dimUPE.append([44.4,300,100,9.5,15,15,56.6,270,240,"M27",50,55,0.968,21.78,7820,522,613,11.8,30.3,538,75.6,137,3.08,33.3,31.5,72.7,2.89,6.03])
    dimUPE.append([53.2,330,105,11,16,18,67.8,298,262,"M27",54,60,1.043,19.6,11010,667,792,12.7,38.8,681,89.7,156,3.17,37.5,45.2,112,2.9,6])
    dimUPE.append([61.2,360,110,12,17,18,77.9,326,290,"M27",55,65,1.121,18.32,14830,824,982,13.8,45.6,844,105,178,3.29,39.5,58.5,166,2.97,6.12])
    dimUPE.append([72.2,400,115,13.5,18,18,91.9,364,328,"M27",57,70,1.218,16.87,20980,1050,1260,15.1,56.2,1045,123,191,3.37,42,79.1,259,2.98,6.06])
    
    return dimUPE

def ProfCorniereEgaleAcier():
    
    dimCorniereEgaleAcier=[]
    #,G,h = b,t,r1,r2,r3,A,zs=ys,v,u1,u2,Ø,e min,e max,A net,AL,AG,Iy=Iz,Wel.y=Wel.z,iy=iz,Iu,iu,Iv,iv, Iyz,
    #,kg/m, mm,mm,mm,mm,mm,mm2,mm,mm,mm,mm,,mm,mm,mm2,m2/m, m2/t,mm4 ,mm3,mm,mm4,mm,mm4,mm,mm4,
    #,,,,,,,x102,,,,,,,,x102,,,x104,x103,x10,x104,x10,x104,x10,x104,
    dimCorniereEgaleAcier.append([0.882,20,3,3.5,"-","-",1.12,0.596,1.41,0.843,0.7,"-","-","-","-",0.077,87.4,0.388,0.276,0.589,0.614,0.74,0.162,0.38,-0.226])
    dimCorniereEgaleAcier.append([1.12,25,3,3.5,"-","-",1.42,0.721,1.77,1.02,0.877,"-","-","-","-",0.097,86.88,0.796,0.448,0.749,1.26,0.944,0.329,0.481,-0.467])
    dimCorniereEgaleAcier.append([1.45,25,4,3.5,"-","-",1.85,0.761,1.77,1.08,0.892,"-","-","-","-",0.097,66.67,1.01,0.582,0.74,1.6,0.93,0.425,0.479,-0.587])
    dimCorniereEgaleAcier.append([1.36,30,3,5,"-","-",1.74,0.835,2.12,1.18,1.05,"-","-","-","-",0.116,84.87,1.4,0.649,0.899,2.23,1.13,0.579,0.578,-0.825])
    dimCorniereEgaleAcier.append([1.78,30,4,5,"-","-",2.27,0.878,2.12,1.24,1.06,"-","-","-","-",0.116,65.02,1.8,0.85,0.892,2.86,1.12,0.749,0.575,-1.05])
    dimCorniereEgaleAcier.append([2.09,35,4,5,"-","-",2.67,1,2.47,1.42,1.24,"-","-","-","-",0.136,64.82,2.95,1.18,1.05,4.69,1.33,1.22,0.68,-1.73])
    dimCorniereEgaleAcier.append([2.57,35,5,5,"-","-",3.28,1.04,2.47,1.48,1.25,"-","-","-","-",0.136,52.76,3.56,1.45,1.04,5.64,1.31,1.49,0.67,-2.08])
    dimCorniereEgaleAcier.append([2.42,40,4,6,"-","-",3.08,1.12,2.83,1.58,1.4,"-","-","-","-",0.155,64.07,4.47,1.55,1.21,7.1,1.52,1.84,0.77,-2.63])
    dimCorniereEgaleAcier.append([2.97,40,5,6,"-","-",3.79,1.16,2.83,1.64,1.41,"-","-","-","-",0.155,52.07,5.43,1.91,1.2,8.61,1.51,2.25,0.77,-3.18])
    dimCorniereEgaleAcier.append([3.52,40,6,6,"-","-",4.48,1.2,2.83,1.7,1.43,"-","-","-","-",0.155,44.04,6.31,2.26,1.19,9.99,1.49,2.64,0.77,-3.67])
    dimCorniereEgaleAcier.append([2.09,45,3,7,"-","-",2.66,1.18,3.18,1.67,1.57,"-","-","-","-",0.174,83.24,4.93,1.49,1.36,7.81,1.71,2.04,0.88,-2.88])
    dimCorniereEgaleAcier.append([2.74,45,4,7,"-","-",3.49,1.23,3.18,1.75,1.57,"-","-","-","-",0.174,63.46,6.43,1.97,1.36,10.21,1.71,2.65,0.87,-3.78])
    dimCorniereEgaleAcier.append([3.06,45,4.5,7,"-","-",3.9,1.26,3.18,1.78,1.58,"-","-","-","-",0.174,56.83,7.15,2.2,1.35,11.35,1.71,2.95,0.87,-4.2])
    dimCorniereEgaleAcier.append([3.38,45,5,7,"-","-",4.3,1.28,3.18,1.81,1.58,"-","-","-","-",0.174,51.51,7.84,2.43,1.35,12.45,1.7,3.24,0.87,-4.6])
    dimCorniereEgaleAcier.append([4,45,6,7,"-","-",5.09,1.32,3.18,1.87,1.59,"-","-","-","-",0.174,43.52,9.16,2.88,1.34,14.52,1.69,3.81,0.86,-5.36])
    dimCorniereEgaleAcier.append([4.6,45,7,7,"-","-",5.86,1.36,3.18,1.92,1.61,"-","-","-","-",0.174,37.81,10.4,3.31,1.33,16.44,1.67,4.36,0.86,-6.04])
    dimCorniereEgaleAcier.append([3.06,50,4,7,"-","-",3.89,1.36,3.54,1.92,1.75,"-","-","-","-",0.194,63.49,8.97,2.46,1.52,14.25,1.91,3.7,0.97,-5.28])
    dimCorniereEgaleAcier.append([3.77,50,5,7,"-","-",4.8,1.4,3.54,1.99,1.76,"-","-","-","-",0.194,51.46,10.96,3.05,1.51,17.41,1.9,4.52,0.97,-6.45])
    dimCorniereEgaleAcier.append([4.47,50,6,7,"-","-",5.69,1.45,3.54,2.04,1.77,"-","-","-","-",0.194,43.41,12.84,3.61,1.5,20.37,1.89,5.31,0.97,-7.53])
    dimCorniereEgaleAcier.append([5.15,50,7,7,"-","-",6.56,1.49,3.54,2.1,1.78,"-","-","-","-",0.194,37.66,14.61,4.16,1.49,23.14,1.88,6.09,0.96,-8.52])
    dimCorniereEgaleAcier.append([5.82,50,8,7,"-","-",7.41,1.52,3.54,2.16,1.8,"-","-","-","-",0.194,33.34,16.28,4.68,1.48,25.71,1.86,6.85,0.96,-9.43])
    dimCorniereEgaleAcier.append([6.47,50,9,7,"-","-",8.24,1.56,3.54,2.21,1.82,"-","-","-","-",0.194,29.98,17.86,5.2,1.47,28.11,1.85,7.61,0.96,-10.25])
    dimCorniereEgaleAcier.append([3.38,55,4,8,"-","-",4.31,1.47,3.89,2.08,1.92,"-","-","-","-",0.213,63.01,12,2.98,1.67,19.05,2.1,4.95,1.07,-7.05])
    dimCorniereEgaleAcier.append([4.18,55,5,8,"-","-",5.32,1.52,3.89,2.15,1.93,"-","-","-","-",0.213,51.05,14.71,3.7,1.66,23.37,2.1,6.06,1.07,-8.66])
    dimCorniereEgaleAcier.append([4.95,55,6,8,"-","-",6.31,1.56,3.89,2.21,1.94,"-","-","-","-",0.213,43.04,17.29,4.39,1.66,27.44,2.09,7.13,1.06,-10.16])
    dimCorniereEgaleAcier.append([3.7,60,4,8,"-","-",4.71,1.6,4.24,2.26,2.1,"M12",34,40.5,4.15,0.233,63.07,15.78,3.58,1.83,25.04,2.31,6.51,1.18,-9.26])
    dimCorniereEgaleAcier.append([4.57,60,5,8,"-","-",5.82,1.64,4.24,2.32,2.11,"M12",35,40.5,5.12,0.233,51.04,19.37,4.45,1.82,30.77,2.3,7.97,1.17,-11.4])
    dimCorniereEgaleAcier.append([5.42,60,6,8,"-","-",6.91,1.69,4.24,2.39,2.11,"M12",36,40.5,6.07,0.233,42.99,22.79,5.29,1.82,36.2,2.29,9.38,1.17,-13.41])
    dimCorniereEgaleAcier.append([6.26,60,7,8,"-","-",7.98,1.73,4.24,2.45,2.13,"M12",28,37,7,0.233,37.22,26.05,6.1,1.81,41.34,2.28,10.76,1.16,-15.23])
    dimCorniereEgaleAcier.append([7.09,60,8,8,"-","-",9.03,1.77,4.24,2.5,2.14,"M12",29,37,7.91,0.233,32.89,29.15,6.89,1.8,46.19,2.26,12.11,1.16,-17.04])
    dimCorniereEgaleAcier.append([8.69,60,10,8,"-","-",11.1,1.85,4.24,2.61,2.17,"M12",31,37,9.67,0.233,26.83,34.93,8.41,1.78,55.1,2.23,14.76,1.15,-20.17])
    dimCorniereEgaleAcier.append([4.82,63,5,9,"-","-",6.14,1.71,4.45,2.42,2.21,"M16",30,34,5.24,0.244,50.71,22.42,4.88,1.91,35.61,2.41,9.24,1.23,-13.18])
    dimCorniereEgaleAcier.append([5.72,63,6,9,"-","-",7.29,1.75,4.45,2.48,2.21,"M16",31,34,6.21,0.244,42.7,26.44,5.82,1.9,41.99,2.4,10.89,1.22,-15.55])
    dimCorniereEgaleAcier.append([6.17,63,6.5,9,"-","-",7.85,1.78,4.45,2.51,2.22,"M16",32,34,6.68,0.244,39.62,28.37,6.27,1.9,45.06,2.4,11.69,1.22,-16.68])
    dimCorniereEgaleAcier.append([4.02,65,4,9,"-","-",5.13,1.71,4.6,2.41,2.28,"M16",29,36,4.41,0.252,62.68,20.09,4.19,1.98,31.86,2.49,8.32,1.27,-11.77])
    dimCorniereEgaleAcier.append([4.97,65,5,9,"-","-",6.34,1.76,4.6,2.49,2.28,"M16",30,36,5.44,0.252,50.71,24.74,5.22,1.98,39.29,2.49,10.19,1.27,-14.55])
    dimCorniereEgaleAcier.append([5.91,65,6,9,"-","-",7.53,1.8,4.6,2.55,2.28,"M16",31,36,6.45,0.252,42.7,29.19,6.21,1.97,46.36,2.48,12.01,1.26,-17.17])
    dimCorniereEgaleAcier.append([6.83,65,7,9,"-","-",8.7,1.85,4.6,2.61,2.29,"M16",32,36,7.44,0.252,36.95,33.43,7.18,1.96,53.08,2.47,13.78,1.26,-19.65])
    dimCorniereEgaleAcier.append([7.73,65,8,9,"-","-",9.85,1.89,4.6,2.67,2.31,"M16",33,36,8.41,0.252,32.64,37.49,8.13,1.95,59.46,2.46,15.52,1.26,-21.97])
    dimCorniereEgaleAcier.append([8.62,65,9,9,"-","-",11,1.93,4.6,2.73,2.32,"M16",34,36,9.36,0.252,29.28,41.37,9.05,1.94,65.52,2.44,17.22,1.25,-24.15])
    dimCorniereEgaleAcier.append([9.49,65,10,9,"-","-",12.1,1.97,4.6,2.78,2.34,"M16",35,36,10.3,0.252,26.59,45.08,9.94,1.93,71.26,2.43,18.91,1.25,-26.17])
    dimCorniereEgaleAcier.append([10.3,65,11,9,"-","-",13.2,2,4.6,2.83,2.35,"M16",36,36,11.2,0.252,24.39,48.64,10.82,1.92,76.69,2.41,20.58,1.25,-28.06])
    dimCorniereEgaleAcier.append([5.37,70,5,9,"-","-",6.84,1.88,4.95,2.66,2.46,"M16",30,41,5.94,0.272,50.73,31.24,6.1,2.14,49.61,2.69,12.86,1.37,-18.37])
    dimCorniereEgaleAcier.append([6.38,70,6,9,"-","-",8.13,1.93,4.95,2.73,2.46,"M16",31,41,7.05,0.272,42.68,36.88,7.27,2.13,58.6,2.69,15.16,1.37,-21.72])
    dimCorniereEgaleAcier.append([7.38,70,7,9,"-","-",9.4,1.97,4.95,2.79,2.47,"M16",32,41,8.14,0.272,36.91,42.3,8.41,2.12,67.19,2.67,17.41,1.36,-24.89])
    dimCorniereEgaleAcier.append([8.37,70,8,10,"-","-",10.7,2.01,4.95,2.84,2.47,"M16",34,41,9.23,0.271,32.41,47.27,9.46,2.1,75.01,2.65,19.52,1.35,-27.75])
    dimCorniereEgaleAcier.append([9.32,70,9,9,"-","-",11.9,2.05,4.95,2.9,2.5,"M16",34,41,10.3,0.272,29.2,52.47,10.6,2.1,83.18,2.65,21.76,1.35,-30.71])
    dimCorniereEgaleAcier.append([10.3,70,10,9,"-","-",13.1,2.09,4.95,2.96,2.51,"M16",35,41,11.3,0.272,26.5,57.24,11.66,2.09,90.6,2.63,23.88,1.35,-33.36])
    dimCorniereEgaleAcier.append([4.65,75,4,9,"-","-",5.93,1.96,5.3,2.76,2.63,"M16",29,46,5.21,0.292,62.82,31.43,5.67,2.3,49.85,2.9,13.01,1.48,-18.42])
    dimCorniereEgaleAcier.append([5.76,75,5,9,"-","-",7.34,2.01,5.3,2.84,2.63,"M16",30,46,6.44,0.292,50.75,38.77,7.06,2.3,61.59,2.9,15.96,1.47,-22.82])
    dimCorniereEgaleAcier.append([6.85,75,6,9,"-","-",8.73,2.05,5.3,2.9,2.64,"M16",31,46,7.65,0.292,42.66,45.83,8.41,2.29,72.84,2.89,18.82,1.47,-27.01])
    dimCorniereEgaleAcier.append([7.93,75,7,9,"-","-",10.1,2.1,5.3,2.96,2.65,"M16",32,46,8.84,0.292,36.88,52.61,9.74,2.28,83.6,2.88,21.62,1.46,-30.99])
    dimCorniereEgaleAcier.append([8.99,75,8,9,"-","-",11.4,2.14,5.3,3.02,2.66,"M16",33,46,10,0.292,32.53,59.13,11.03,2.27,93.91,2.86,24.35,1.46,-34.78])
    dimCorniereEgaleAcier.append([10,75,9,9,"-","-",12.8,2.18,5.3,3.08,2.67,"M16",34,46,11.2,0.292,29.14,65.4,12.29,2.26,103.8,2.85,27.03,1.45,-38.36])
    dimCorniereEgaleAcier.append([11.1,75,10,9,"-","-",14.1,2.22,5.3,3.13,2.69,"M16",35,46,12.3,0.292,26.43,71.43,13.52,2.25,113.2,2.83,29.68,1.45,-41.75])
    dimCorniereEgaleAcier.append([6.17,80,5,10,"-","-",7.86,2.12,5.66,3,2.81,"M16",31,51,6.96,0.311,50.49,47.14,8.02,2.45,74.83,3.09,19.45,1.57,-27.69])
    dimCorniereEgaleAcier.append([7.34,80,6,10,"-","-",9.35,2.17,5.66,3.07,2.81,"M16",32,51,8.27,0.311,42.44,55.82,9.57,2.44,88.69,3.08,22.96,1.57,-32.87])
    dimCorniereEgaleAcier.append([8.49,80,7,10,"-","-",10.8,2.21,5.66,3.13,2.82,"M16",33,51,9.56,0.311,36.67,64.19,11.09,2.44,102,3.07,26.38,1.56,-37.81])
    dimCorniereEgaleAcier.append([9.63,80,8,10,"-","-",12.3,2.26,5.66,3.19,2.83,"M16",34,51,10.8,0.311,32.34,72.25,12.58,2.43,114.8,3.06,29.72,1.56,-42.52])
    dimCorniereEgaleAcier.append([10.8,80,9,10,"-","-",13.7,2.3,5.66,3.25,2.84,"M16",35,51,12.1,0.311,28.96,80.01,14.03,2.42,127,3.05,33.01,1.55,-47.01])
    dimCorniereEgaleAcier.append([11.9,80,10,10,"-","-",15.1,2.34,5.66,3.3,2.85,"M16",36,51,13.3,0.311,26.26,87.5,15.45,2.41,138.8,3.03,36.24,1.55,-51.27])
    dimCorniereEgaleAcier.append([6.97,90,5,11,"-","-",8.88,2.35,6.36,3.33,3.16,"M20",35,55,7.78,0.351,50.29,67.67,10.18,2.76,107.3,3.48,27.98,1.78,-39.68])
    dimCorniereEgaleAcier.append([8.28,90,6,10,"-","-",10.5,2.42,6.36,3.42,3.16,"M20",36,55,9.23,0.351,42.44,80.72,12.26,2.77,128.3,3.49,33.16,1.77,-47.57])
    dimCorniereEgaleAcier.append([9.61,90,7,11,"-","-",12.2,2.45,6.36,3.47,3.16,"M20",38,55,10.7,0.351,36.48,92.55,14.13,2.75,147.1,3.47,38.03,1.76,-54.52])
    dimCorniereEgaleAcier.append([10.9,90,8,11,"-","-",13.9,2.5,6.36,3.53,3.17,"M20",39,55,12.1,0.351,32.15,104.4,16.05,2.74,165.9,3.46,42.89,1.76,-61.5])
    dimCorniereEgaleAcier.append([12.2,90,9,11,"-","-",15.5,2.54,6.36,3.59,3.18,"M20",40,55,13.5,0.351,28.77,115.8,17.93,2.73,184,3.44,47.65,1.75,-68.19])
    dimCorniereEgaleAcier.append([13.4,90,10,11,"-","-",17.1,2.58,6.36,3.65,3.19,"M20",41,55,14.9,0.351,26.07,126.9,19.77,2.72,201.5,3.43,52.33,1.75,-74.59])
    dimCorniereEgaleAcier.append([14.7,90,11,11,"-","-",18.7,2.62,6.36,3.7,3.21,"M20",42,55,16.3,0.351,23.86,137.6,21.57,2.71,218.3,3.42,56.94,1.74,-80.7])
    dimCorniereEgaleAcier.append([20.7,90,16,11,"-","-",26.4,2.81,6.36,3.97,3.29,"M20",47,55,22.8,0.351,16.93,186.4,30.11,2.66,293.5,3.34,79.4,1.74,-107])
    dimCorniereEgaleAcier.append([9.26,100,6,12,"-","-",11.8,2.64,7.07,3.74,3.51,"M24",41,59,10.2,0.39,42.09,111.1,15.09,3.07,176.3,3.87,45.8,1.97,-65.25])
    dimCorniereEgaleAcier.append([10.7,100,7,12,"-","-",13.7,2.69,7.07,3.81,3.51,"M24",42,59,11.8,0.39,36.33,128.2,17.54,3.06,203.7,3.86,52.72,1.96,-75.48])
    dimCorniereEgaleAcier.append([12.2,100,8,12,"-","-",15.5,2.74,7.07,3.87,3.52,"M24",43,59,13.4,0.39,32,144.8,19.94,3.06,230.2,3.85,59.49,1.96,-85.35])
    dimCorniereEgaleAcier.append([13.6,100,9,12,"-","-",17.3,2.78,7.07,3.93,3.53,"M24",44,59,15,0.39,28.62,161,22.3,3.05,255.9,3.84,66.13,1.95,-94.86])
    dimCorniereEgaleAcier.append([15,100,10,12,"-","-",19.2,2.82,7.07,3.99,3.54,"M24",45,59,16.6,0.39,25.92,176.7,24.62,3.04,280.7,3.83,72.66,1.95,-104])
    dimCorniereEgaleAcier.append([16.4,100,11,12,"-","-",20.9,2.86,7.07,4.05,3.55,"M24",46,59,18.1,0.39,23.7,191.9,26.89,3.03,304.7,3.81,79.09,1.94,-112.8])
    dimCorniereEgaleAcier.append([17.8,100,12,12,"-","-",22.7,2.9,7.07,4.11,3.57,"M24",47,59,19.6,0.39,21.86,206.7,29.12,3.02,327.9,3.8,85.44,1.94,-121.3])
    dimCorniereEgaleAcier.append([20.6,100,14,12,"-","-",26.2,2.98,7.07,4.22,3.6,"M24",49,59,22.6,0.39,18.95,235,33.48,3,372.1,3.77,97.92,1.93,-137.1])
    dimCorniereEgaleAcier.append([23.2,100,16,12,"-","-",29.6,3.06,7.07,4.32,3.63,"M24",52,59,25.4,0.39,16.77,261.7,37.7,2.97,413.3,3.74,110.2,1.93,-151.5])
    dimCorniereEgaleAcier.append([10.2,110,6,12,"-","-",13,2.89,7.78,4.09,3.87,"M27",45,62,11.2,0.43,42.12,149.5,18.43,3.39,237.3,4.27,61.6,2.18,-87.87])
    dimCorniereEgaleAcier.append([11.8,110,7,12,"-","-",15.1,2.94,7.78,4.16,3.87,"M27",45,62,13,0.43,36.34,172.7,21.43,3.39,274.4,4.27,70.94,2.17,-101.7])
    dimCorniereEgaleAcier.append([13.4,110,8,12,"-","-",17.1,2.99,7.78,4.22,3.87,"M27",46,62,14.7,0.43,31.98,195.3,24.37,3.38,310.5,4.26,80.11,2.16,-115.2])
    dimCorniereEgaleAcier.append([15,110,9,12,"-","-",19.1,3.03,7.78,4.28,3.88,"M27",47,62,16.4,0.43,28.59,217.3,27.26,3.37,345.5,4.25,89.1,2.16,-128.2])
    dimCorniereEgaleAcier.append([16.6,110,10,13,"-","-",21.2,3.06,7.78,4.33,3.88,"M27",49,62,18.2,0.429,25.79,238,29.99,3.35,378.2,4.23,97.74,2.15,-140.2])
    dimCorniereEgaleAcier.append([18.2,110,11,13,"-","-",23.2,3.11,7.78,4.39,3.89,"M27",50,62,19.9,0.429,23.58,258.8,32.79,3.34,411.2,4.21,106.4,2.14,-152.4])
    dimCorniereEgaleAcier.append([19.7,110,12,13,"-","-",25.1,3.15,7.78,4.45,3.91,"M27",51,62,21.5,0.429,21.73,279.1,35.54,3.33,443.2,4.2,115,2.14,-164.1])
    dimCorniereEgaleAcier.append([12.9,120,7,13,"-","-",16.5,3.18,8.49,4.49,4.22,"M27",46,72,14.4,0.469,36.22,225.6,25.57,3.7,358.4,4.66,92.8,2.37,-132.8])
    dimCorniereEgaleAcier.append([14.7,120,8,13,"-","-",18.7,3.23,8.49,4.56,4.22,"M27",48,72,16.3,0.469,31.87,255.4,29.11,3.69,406,4.65,104.8,2.37,-150.6])
    dimCorniereEgaleAcier.append([16.5,120,9,13,"-","-",21,3.27,8.49,4.62,4.23,"M27",48,72,18.3,0.469,28.48,284.5,32.59,3.68,452.4,4.64,116.7,2.36,-167.9])
    dimCorniereEgaleAcier.append([18.2,120,10,13,"-","-",23.2,3.31,8.49,4.69,4.24,"M27",49,72,20.2,0.469,25.76,312.9,36.03,3.67,497.6,4.63,128.3,2.35,-184.6])
    dimCorniereEgaleAcier.append([19.9,120,11,13,"-","-",25.4,3.36,8.49,4.75,4.25,"M27",50,72,22.1,0.469,23.54,340.6,39.41,3.66,541.5,4.62,139.8,2.35,-200.9])
    dimCorniereEgaleAcier.append([21.6,120,12,13,"-","-",27.5,3.4,8.49,4.8,4.26,"M27",51,72,23.9,0.469,21.69,367.7,42.73,3.65,584.3,4.61,151.1,2.34,-216.6])
    dimCorniereEgaleAcier.append([23.3,120,13,13,"-","-",29.7,3.44,8.49,4.86,4.28,"M27",52,72,25.8,0.469,20.12,394,46.01,3.64,625.8,4.59,162.2,2.34,-231.8])
    dimCorniereEgaleAcier.append([25,120,14,13,"-","-",31.8,3.48,8.49,4.92,4.29,"M27",53,72,27.6,0.469,18.77,419.8,49.25,3.63,666.3,4.58,173.3,2.33,-246.5])
    dimCorniereEgaleAcier.append([26.6,120,15,13,"-","-",33.9,3.51,8.49,4.97,4.31,"M27",54,72,29.4,0.469,17.6,444.9,52.43,3.62,705.6,4.56,184.2,2.33,-260.7])
    dimCorniereEgaleAcier.append([28.3,120,16,13,"-","-",36,3.55,8.49,5.02,4.32,"M27",56,72,31.2,0.469,16.58,469.4,55.57,3.61,743.8,4.54,195,2.33,-274.4])
    dimCorniereEgaleAcier.append([16,130,8,14,"-","-",20.4,3.46,9.19,4.9,4.57,"M27",48,82,18,0.508,31.77,326.7,34.26,4,519.2,5.05,134.3,2.57,-192.5])
    dimCorniereEgaleAcier.append([17.9,130,9,14,"-","-",22.8,3.51,9.19,4.96,4.57,"M27",49,82,20.1,0.508,28.38,364.4,38.39,4,579.2,5.04,149.5,2.56,-214.9])
    dimCorniereEgaleAcier.append([19.8,130,10,14,"-","-",25.2,3.55,9.19,5.03,4.58,"M27",50,82,22.2,0.508,25.67,401.1,42.47,3.99,637.8,5.03,164.5,2.55,-236.7])
    dimCorniereEgaleAcier.append([21.7,130,11,14,"-","-",27.6,3.6,9.19,5.09,4.59,"M27",51,82,24.3,0.508,23.45,437.1,46.48,3.98,694.9,5.02,179.2,2.55,-257.9])
    dimCorniereEgaleAcier.append([23.5,130,12,14,"-","-",30,3.64,9.19,5.15,4.6,"M27",52,82,26.4,0.508,21.59,472.2,50.44,3.97,750.6,5,193.7,2.54,-278.4])
    dimCorniereEgaleAcier.append([25.4,130,13,14,"-","-",32.3,3.68,9.19,5.2,4.62,"M27",53,82,28.4,0.508,20.02,506.5,54.35,3.96,804.9,4.99,208.1,2.54,-298.4])
    dimCorniereEgaleAcier.append([27.2,130,14,14,"-","-",34.7,3.72,9.19,5.26,4.63,"M27",54,82,30.5,0.508,18.68,540.1,58.2,3.95,857.8,4.98,222.3,2.53,-317.8])
    dimCorniereEgaleAcier.append([29,130,15,14,"-","-",37,3.76,9.19,5.32,4.65,"M27",57,82,32.5,0.508,17.51,572.9,62,3.94,909.4,4.96,236.3,2.53,-336.5])
    dimCorniereEgaleAcier.append([30.8,130,16,14,"-","-",39.3,3.8,9.19,5.37,4.66,"M27",27,82,34.5,0.508,16.49,605,65.75,3.93,959.7,4.94,250.3,2.53,-354.7])
    dimCorniereEgaleAcier.append([19.3,140,9,15,"-","-",24.6,3.75,9.9,5.3,4.92,"M27",50,92,21.9,0.547,28.3,457.8,44.66,4.31,727.6,5.44,188,2.76,-269.8])
    dimCorniereEgaleAcier.append([21.4,140,10,15,"-","-",27.2,3.79,9.9,5.37,4.93,"M27",51,92,24.2,0.547,25.59,504.4,49.43,4.3,802,5.43,206.9,2.76,-297.6])
    dimCorniereEgaleAcier.append([23.4,140,11,15,"-","-",29.8,3.84,9.9,5.43,4.94,"M27",52,92,26.5,0.547,23.36,550.1,54.14,4.29,874.7,5.41,225.5,2.75,-324.6])
    dimCorniereEgaleAcier.append([25.4,140,12,15,"-","-",32.4,3.88,9.9,5.49,4.95,"M27",53,92,28.8,0.547,21.51,594.8,58.78,4.28,945.7,5.4,243.9,2.74,-350.9])
    dimCorniereEgaleAcier.append([27.5,140,13,15,"-","-",35,3.92,9.9,5.55,4.96,"M27",54,92,31.1,0.547,19.94,638.5,63.37,4.27,1015,5.39,262,2.74,-376.5])
    dimCorniereEgaleAcier.append([29.4,140,14,15,"-","-",37.5,3.96,9.9,5.61,4.97,"M27",55,92,33.3,0.547,18.6,681.4,67.89,4.26,1083,5.37,280,2.73,-401.4])
    dimCorniereEgaleAcier.append([31.4,140,15,15,"-","-",40,4,9.9,5.66,4.99,"M27",56,92,35.5,0.547,17.43,723.3,72.36,4.25,1149,5.36,297.7,2.73,-425.6])
    dimCorniereEgaleAcier.append([33.3,140,16,15,"-","-",42.5,4.04,9.9,5.72,5,"M27",58,92,37.7,0.547,16.41,764.4,76.77,4.24,1214,5.34,315.2,2.72,-449.2])
    dimCorniereEgaleAcier.append([23,150,10,16,"-","-",29.3,4.03,10.61,5.71,5.28,"M27",52,102,26.3,0.586,25.51,624,56.91,4.62,992,5.82,256.1,2.96,-368])
    dimCorniereEgaleAcier.append([27.3,150,12,16,"-","-",34.8,4.12,10.61,5.83,5.29,"M27",54,102,31.2,0.586,21.44,736.9,67.75,4.6,1172,5.8,302.1,2.94,-434.9])
    dimCorniereEgaleAcier.append([29.5,150,13,16,"-","-",37.6,4.17,10.61,5.89,5.3,"M27",55,102,33.7,0.586,19.87,791.7,73.07,4.59,1259,5.79,324.6,2.94,-467.1])
    dimCorniereEgaleAcier.append([31.6,150,14,16,"-","-",40.3,4.21,10.61,5.95,5.32,"M27",56,102,36.1,0.586,18.53,845.4,78.33,4.58,1344,5.77,346.9,2.93,-498.5])
    dimCorniereEgaleAcier.append([33.8,150,15,16,"-","-",43,4.25,10.61,6.01,5.33,"M27",5,102,38.5,0.586,17.36,898.1,83.52,4.57,1427,5.76,369,2.93,-529.1])
    dimCorniereEgaleAcier.append([35.9,150,16,16,"-","-",45.7,4.29,10.61,6.06,5.34,"M27",58,102,40.9,0.586,16.34,949.7,88.65,4.56,1509,5.74,390.8,2.92,-558.9])
    dimCorniereEgaleAcier.append([40.1,150,18,16,"-","-",51,4.37,10.61,6.17,5.37,"M27",61,102,45.6,0.586,14.63,1050,98.74,4.54,1666,5.71,433.8,2.92,-616.1])
    dimCorniereEgaleAcier.append([44.2,150,20,16,"-","-",56.3,4.44,10.61,6.28,5.41,"M27",63,102,50.3,0.586,13.27,1146,108.6,4.51,1817,5.68,476.2,2.91,-670.2])
    dimCorniereEgaleAcier.append([33.9,160,14,17,"-","-",43.2,4.45,11.31,6.29,5.66,"M27",57,111,39,0.625,18.46,1034,89.5,4.89,1644,6.17,423.9,3.13,-609.9])
    dimCorniereEgaleAcier.append([36.2,160,15,17,"-","-",46.1,4.49,11.31,6.35,5.67,"M27",58,111,41.6,0.625,17.3,1099,95.47,4.88,1747,6.16,450.9,3.13,-647.9])
    dimCorniereEgaleAcier.append([38.4,160,16,17,"-","-",49,4.53,11.31,6.41,5.69,"M27",60,111,44.2,0.625,16.28,1163,101.4,4.87,1848,6.14,477.7,3.12,-685])
    dimCorniereEgaleAcier.append([40.7,160,17,17,"-","-",51.8,4.57,11.31,6.46,5.7,"M27",61,111,46.7,0.625,15.37,1225,107.2,4.86,1947,6.13,504.2,3.12,-721.2])
    dimCorniereEgaleAcier.append([42.9,160,18,17,"-","-",54.7,4.61,11.31,6.52,5.71,"M27",62,111,49.3,0.625,14.57,1287,113,4.85,2043,6.11,530.4,3.11,-756.5])
    dimCorniereEgaleAcier.append([45.1,160,19,17,"-","-",57.5,4.65,11.31,6.58,5.73,"M27",63,111,51.8,0.625,13.86,1347,118.7,4.84,2138,6.1,556.5,3.11,-790.9])
    dimCorniereEgaleAcier.append([35.7,180,13,18,"-","-",45.5,4.9,12.73,6.93,6.35,"M27",57,131,41.6,0.705,19.74,1396,106.5,5.54,2220,6.99,571.7,3.55,-824.4])
    dimCorniereEgaleAcier.append([38.3,180,14,18,"-","-",48.8,4.94,12.73,6.99,6.36,"M27",58,131,44.6,0.705,18.4,1493,114.3,5.53,2375,6.98,611.4,3.54,-881.8])
    dimCorniereEgaleAcier.append([40.9,180,15,18,"-","-",52.1,4.98,12.73,7.05,6.37,"M27",59,131,47.6,0.705,17.23,1589,122,5.52,2527,6.96,650.6,3.53,-938])
    dimCorniereEgaleAcier.append([43.5,180,16,18,"-","-",55.4,5.02,12.73,7.1,6.38,"M27",61,131,50.6,0.705,16.2,1682,129.7,5.51,2675,6.95,689.4,3.53,-993])
    dimCorniereEgaleAcier.append([46,180,17,18,"-","-",58.7,5.06,12.73,7.16,6.4,"M27",62,131,53.6,0.705,15.3,1775,137.2,5.5,2822,6.94,727.9,3.52,-1047])
    dimCorniereEgaleAcier.append([48.6,180,18,18,"-","-",61.9,5.1,12.73,7.22,6.41,"M27",63,131,56.5,0.705,14.5,1866,144.7,5.49,2965,6.92,766,3.52,-1100])
    dimCorniereEgaleAcier.append([51.1,180,19,18,"-","-",65.1,5.14,12.73,7.27,6.42,"M27",64,131,59.4,0.705,13.78,1955,152.1,5.48,3106,6.91,803.8,3.51,-1151])
    dimCorniereEgaleAcier.append([53.7,180,20,18,"-","-",68.3,5.18,12.73,7.33,6.44,"M27",65,131,62.3,0.705,13.13,2043,159.4,5.47,3244,6.89,841.3,3.51,-1202])
    dimCorniereEgaleAcier.append([39.8,200,13,18,"-","-",50.7,5.4,14.14,7.63,7.06,"M27",57,151,46.8,0.785,19.73,1939,132.8,6.19,3085,7.8,792.8,3.96,-1146])
    dimCorniereEgaleAcier.append([45.6,200,15,18,"-","-",58.1,5.48,14.14,7.75,7.08,"M27",59,151,53.6,0.785,17.2,2209,152.2,6.17,3516,7.78,903,3.94,-1306])
    dimCorniereEgaleAcier.append([48.5,200,16,18,"-","-",61.8,5.52,14.14,7.81,7.09,"M27",61,151,57,0.785,16.18,2341,161.7,6.16,3725,7.76,957.2,3.94,-1384])
    dimCorniereEgaleAcier.append([51.4,200,17,18,"-","-",65.5,5.56,14.14,7.87,7.1,"M27",62,151,60.4,0.785,15.27,2472,171.2,6.14,3932,7.75,1011,3.93,-1461])
    dimCorniereEgaleAcier.append([54.2,200,18,18,"-","-",69.1,5.6,14.14,7.93,7.12,"M27",63,151,63.7,0.785,14.46,2600,180.6,6.13,4135,7.74,1064,3.92,-1535])
    dimCorniereEgaleAcier.append([57.1,200,19,18,"-","-",72.7,5.64,14.14,7.98,7.13,"M27",64,151,67,0.785,13.74,2726,189.9,6.12,4335,7.72,1117,3.92,-1609])
    dimCorniereEgaleAcier.append([59.9,200,20,18,"-","-",76.3,5.68,14.14,8.04,7.15,"M27",65,151,70.3,0.785,13.09,2851,199.1,6.11,4532,7.7,1169,3.91,-1681])
    dimCorniereEgaleAcier.append([62.8,200,21,18,"-","-",79.9,5.72,14.14,8.09,7.16,"M27",66,151,73.6,0.785,12.5,2973,208.2,6.1,4725,7.69,1221,3.91,-1752])
    dimCorniereEgaleAcier.append([65.6,200,22,18,"-","-",83.5,5.76,14.14,8.15,7.18,"M27",67,151,76.9,0.785,11.97,3094,217.3,6.09,4915,7.67,1273,3.9,-1821])
    dimCorniereEgaleAcier.append([68.3,200,23,18,"-","-",87.1,5.8,14.14,8.2,7.19,"M27",68,151,80.2,0.785,11.48,3213,226.3,6.08,5102,7.66,1324,3.9,-1889])
    dimCorniereEgaleAcier.append([71.1,200,24,18,"-","-",90.6,5.84,14.14,8.26,7.21,"M27",69,151,83.4,0.785,11.03,3331,235.2,6.06,5286,7.64,1375,3.9,-1955])
    dimCorniereEgaleAcier.append([73.9,200,25,18,"-","-",94.1,5.88,14.14,8.31,7.23,"M27",70,151,86.6,0.785,10.62,3446,244,6.05,5467,7.62,1426,3.89,-2020])
    dimCorniereEgaleAcier.append([76.6,200,26,18,"-","-",97.6,5.91,14.14,8.36,7.25,"M27",71,151,89.8,0.785,10.24,3560,252.7,6.04,5644,7.61,1476,3.89,-2084])
    dimCorniereEgaleAcier.append([82,200,28,18,"-","-",105,5.99,14.14,8.47,7.28,"M27",73,151,96.1,0.785,9.56,3784,270,6.02,5991,7.57,1576,3.88,-2207])
    dimCorniereEgaleAcier.append([64.4,250,17,18,9,3,82.1,6.79,17.68,9.6,9.28,"M27",62,201,77,0.98,15.14,4893,268.7,7.72,7789,9.74,1997,4.93,-2896])
    dimCorniereEgaleAcier.append([68.1,250,18,18,9,3,86.7,6.83,17.68,9.66,9.29,"M27",63,201,81.3,0.98,14.33,5156,283.8,7.71,8208,9.73,2104,4.93,-3052])
    dimCorniereEgaleAcier.append([71.7,250,19,18,9,3,91.4,6.87,17.68,9.72,9.3,"M27",64,201,85.7,0.98,13.6,5417,298.9,7.7,8622,9.71,2212,4.92,-3205])
    dimCorniereEgaleAcier.append([75.3,250,20,18,9,3,96,6.91,17.68,9.78,9.31,"M27",65,201,90,0.98,12.95,5674,313.8,7.69,9031,9.7,2318,4.91,-3357])
    dimCorniereEgaleAcier.append([78.9,250,21,18,9,3,100.6,6.96,17.68,9.84,9.33,"M27",66,201,94.3,0.98,12.36,5929,328.6,7.68,9435,9.69,2423,4.91,-3506])
    dimCorniereEgaleAcier.append([82.5,250,22,18,9,3,105.1,7,17.68,9.89,9.34,"M27",67,201,98.5,0.98,11.82,6180,343.3,7.67,9833,9.67,2528,4.9,-3652])
    dimCorniereEgaleAcier.append([86.1,250,23,18,9,3,109.7,7.03,17.68,9.95,9.36,"M27",68,201,103,0.98,11.33,6429,357.8,7.66,10230,9.66,2632,4.9,-3797])
    dimCorniereEgaleAcier.append([89.7,250,24,18,9,3,114.2,7.07,17.68,10,9.37,"M27",69,201,107,0.98,10.88,6674,372.3,7.64,10610,9.64,2735,4.89,-3939])
    dimCorniereEgaleAcier.append([93.2,250,25,18,9,3,118.7,7.11,17.68,10.06,9.39,"M27",70,201,111,0.98,10.47,6917,386.7,7.63,11000,9.63,2837,4.89,-4079])
    dimCorniereEgaleAcier.append([96.7,250,26,18,9,3,123.2,7.15,17.68,10.11,9.4,"M27",71,201,115,0.98,10.09,7156,400.9,7.62,11370,9.61,2939,4.88,-4217])
    dimCorniereEgaleAcier.append([101,250,27,18,9,3,127.7,7.19,17.68,10.17,9.42,"M27",72,201,120,0.98,9.66,7393,415.1,7.61,11750,9.59,3040,4.88,-4353])
    dimCorniereEgaleAcier.append([104,250,28,18,9,3,132.1,7.23,17.68,10.22,9.44,"M27",73,201,124,0.98,9.4,7627,429.2,7.6,12110,9.57,3141,4.88,-4486])
    dimCorniereEgaleAcier.append([107,250,29,18,9,3,136.6,7.27,17.68,10.28,9.45,"M27",74,201,128,0.98,9.1,7858,443.1,7.59,12480,9.56,3241,4.87,-4618])
    dimCorniereEgaleAcier.append([111,250,30,18,9,3,141,7.3,17.68,10.33,9.47,"M27",75,201,132,0.98,8.81,8087,457,7.57,12830,9.54,3340,4.87,-4747])
    dimCorniereEgaleAcier.append([114,250,31,18,9,3,145.4,7.34,17.68,10.38,9.49,"M27",76,201,136,0.98,8.55,8313,470.8,7.56,13190,9.53,3439,4.86,-4874])
    dimCorniereEgaleAcier.append([118,250,32,18,9,3,149.7,7.38,17.68,10.44,9.5,"M27",77,201,140,0.98,8.3,8536,484.4,7.55,13540,9.51,3538,4.86,-4998])
    dimCorniereEgaleAcier.append([121,250,33,18,9,3,154.1,7.42,17.68,10.49,9.52,"M27",78,201,144,0.98,8.06,8757,498,7.54,13880,9.49,3636,4.86,-5121])
    dimCorniereEgaleAcier.append([124,250,34,18,9,3,158.4,7.45,17.68,10.54,9.54,"M27",79,201,148,0.98,7.84,8975,511.5,7.53,14220,9.47,3734,4.86,-5241])
    dimCorniereEgaleAcier.append([128,250,35,18,9,3,162.7,7.49,17.68,10.59,9.56,"M27",80,201,152,0.98,7.64,9191,524.9,7.52,14550,9.46,3832,4.85,-5359])
    dimCorniereEgaleAcier.append([112,300,25,18,12,15,142.7,8.35,21.21,11.8,11.18,"M27",70,251,135,1.17,10.4,12150,561.1,9.23,19370,11.65,4930,5.88,-7220])
    dimCorniereEgaleAcier.append([116,300,26,18,12,15,148.2,8.39,21.21,11.86,11.19,"M27",71,251,140,1.17,10.01,12590,582.5,9.22,20060,11.63,5115,5.87,-7475])
    dimCorniereEgaleAcier.append([121,300,27,18,12,15,153.7,8.43,21.21,11.92,11.21,"M27",72,251,146,1.17,9.66,13020,603.5,9.2,20750,11.62,5294,5.87,-7726])
    dimCorniereEgaleAcier.append([125,300,28,18,12,15,159.1,8.47,21.21,11.97,11.22,"M27",73,251,151,1.17,9.33,13450,624.6,9.19,21420,11.6,5475,5.87,-7975])
    dimCorniereEgaleAcier.append([129,300,29,18,12,15,164.6,8.5,21.21,12.03,11.24,"M27",74,251,156,1.17,9.02,13870,645.2,9.18,22090,11.59,5650,5.86,-8220])
    dimCorniereEgaleAcier.append([133,300,30,18,12,15,170,8.54,21.21,12.08,11.25,"M27",75,251,161,1.17,8.73,14290,666,9.17,22750,11.57,5828,5.86,-8462])
    dimCorniereEgaleAcier.append([138,300,31,18,12,15,175.4,8.58,21.21,12.14,11.27,"M27",76,251,166,1.17,8.46,14700,686.3,9.16,23400,11.55,5999,5.85,-8701])
    dimCorniereEgaleAcier.append([142,300,32,18,12,15,180.7,8.62,21.21,12.19,11.29,"M27",77,251,171,1.17,8.21,15120,707.2,9.15,24050,11.54,6184,5.85,-8936])
    dimCorniereEgaleAcier.append([146,300,33,18,12,15,186.1,8.66,21.21,12.24,11.3,"M27",78,251,176,1.17,7.98,15520,727.2,9.13,24690,11.52,6351,5.84,-9169])
    dimCorniereEgaleAcier.append([150,300,34,18,12,15,191.4,8.7,21.21,12.3,11.32,"M27",79,251,181,1.17,7.75,15930,747.7,9.12,25320,11.5,6532,5.84,-9398])
    dimCorniereEgaleAcier.append([154,300,35,18,12,15,196.7,8.73,21.21,12.35,11.34,"M27",80,251,186,1.17,7.55,16320,767.4,9.11,25950,11.49,6696,5.83,-9624])
    
    return dimCorniereEgaleAcier
    
def ProfCorniereInegaleAcier():
    
    dimCorniereInegaleAcier=[]
    #,G,h,b,t,r1,r2,A,zs,ys,v1,v2,u1,u2,u3,Øz,e z.min,e z.max,A z.net,Øy,e y.min,e y.max,A y.net,AL,AG,Iy,Wel.y,iy,Iz,Wel.z,iz,Iu,iu,Iv,iv, Iyz,a,
    #,kg/m, mm,mm,mm,mm,mm,mm2,mm,mm,mm,mm,mm,mm,mm,mm2,mm,mm,mm2,mm3,mm,mm,mm2,m2/m, m2/t,mm4 ,mm3,mm,mm4 ,mm3,mm,mm4,mm,mm4,mm,mm4,°,
    #,,,,,,,x102,,,,,,,,x102,,,x102,x103,x10,x104,x102,x104,x10,x104,x103,x10,x104,x103,x10,x104,x10,x104,x10,x104,,
    dimCorniereInegaleAcier.append([8.77,100,65,7,10,5,11.2,3.23,1.51,6.83,4.9,2.64,3.44,1.66,"M27",47,54,9.07,"M16",37,38,9.91,0.321,36.66,112.5,16.61,3.17,37.58,7.53,1.83,128.2,3.39,21.89,1.4,-37.7,22.59])
    dimCorniereInegaleAcier.append([9.94,100,65,8,10,5,12.7,3.27,1.55,6.81,4.92,2.69,3.43,1.69,"M27",48,54,10.3,"M16",38,38,11.2,0.321,32.32,126.8,18.85,3.16,42.23,8.54,1.83,144.4,3.38,24.66,1.4,-42.4,22.53])
    dimCorniereInegaleAcier.append([11.1,100,65,9,10,5,14.1,3.32,1.59,6.78,4.94,2.74,3.42,1.72,"M27",49,54,11.4,"M16",39,38,12.5,0.321,28.94,140.6,21.05,3.15,46.7,9.52,1.82,160,3.36,27.37,1.39,-46.8,22.44])
    dimCorniereInegaleAcier.append([12.3,100,65,10,10,5,15.6,3.36,1.63,6.76,4.96,2.79,3.41,1.75,"M27",50,54,12.6,"M16",40,38,13.8,0.321,26.23,154,23.2,3.14,50.98,10.48,1.81,175,3.35,30.03,1.39,-51,22.35])
    dimCorniereInegaleAcier.append([14.5,100,65,12,10,5,18.5,3.44,1.71,6.72,4.99,2.88,3.4,1.81,"M27",52,54,14.9,"M16",42,38,16.3,0.321,22.17,179.6,27.38,3.12,59.07,12.33,1.79,203.4,3.32,35.23,1.38,-58.7,22.11])
    dimCorniereInegaleAcier.append([13.4,110,70,10,10,5,17.1,3.69,1.72,7.43,5.38,2.96,3.73,1.84,"M27",50,64,14.1,"M16",40,43,15.3,0.351,26.17,206.6,28.27,3.48,65.07,12.31,1.95,233.2,3.69,38.54,1.5,-66.8,21.67])
    dimCorniereInegaleAcier.append([15.9,110,70,12,10,5,20.3,3.77,1.79,7.38,5.42,3.05,3.72,1.9,"M27",52,64,16.7,"M16",42,43,18.1,0.351,22.09,241.5,33.4,3.45,75.54,14.51,1.93,271.8,3.66,45.22,1.49,-77.1,21.46])
    dimCorniereInegaleAcier.append([12.2,120,80,8,11,5.5,15.5,3.83,1.87,8.23,5.97,3.25,4.19,2.09,"M27",48,72,13.1,"M16",38,50,14,0.391,32.12,225.7,27.63,3.82,80.76,13.17,2.28,260,4.1,46.39,1.73,-78.5,23.65])
    dimCorniereInegaleAcier.append([15,120,80,10,11,5.5,19.1,3.92,1.95,8.19,6.01,3.35,4.17,2.15,"M27",50,72,16.1,"M16",40,50,17.3,0.391,26.01,275.5,34.1,3.8,98.11,16.21,2.26,317,4.07,56.6,1.72,-95.3,23.53])
    dimCorniereInegaleAcier.append([17.8,120,80,12,11,5.5,22.7,4,2.03,8.14,6.04,3.45,4.16,2.2,"M27",52,72,19.1,"M16",42,50,20.5,0.391,21.93,322.8,40.37,3.77,114.3,19.14,2.24,370.7,4.04,66.45,1.71,-110.8,23.37])
    dimCorniereInegaleAcier.append([16.6,130,90,10,11,5,21.2,4.16,2.19,8.93,6.67,3.75,4.62,2.49,"M27",50,84,18.2,"M24",50,51,18.6,0.431,25.96,359.7,40.7,4.12,141.8,20.82,2.59,421.5,4.46,79.92,1.94,-131.6,25.19])
    dimCorniereInegaleAcier.append([19.7,130,90,12,11,5,25.1,4.24,2.26,8.9,6.69,3.84,4.59,2.51,"M27",52,83,21.5,"M24",52,51,22,0.43,21.8,420.4,47.97,4.09,164.5,24.42,2.56,491.6,4.42,93.31,1.93,-152.6,25.02])
    dimCorniereInegaleAcier.append([22.8,130,90,14,11,5,29,4.33,2.34,8.85,6.73,3.95,4.61,2.6,"M27",54,84,24.8,"M24",54,51,25.4,0.431,18.94,481.4,55.5,4.07,187.9,28.24,2.55,561.9,4.4,107.4,1.93,-173.5,24.89])
    dimCorniereInegaleAcier.append([14,140,90,8,11,5.5,17.9,4.49,2.03,9.56,6.81,3.58,4.83,2.27,"M27",48,93,15.5,"M24",48,51,15.8,0.451,32.08,360,37.86,4.49,118.2,16.96,2.57,409.3,4.78,68.9,1.96,-119.8,22.38])
    dimCorniereInegaleAcier.append([17.4,140,90,10,11,5.5,22.1,4.58,2.11,9.52,6.85,3.69,4.81,2.33,"M27",50,93,19.1,"M24",50,51,19.5,0.451,25.94,440.9,46.81,4.46,144.1,20.91,2.55,500.8,4.76,84.19,1.95,-146.2,22.28])
    dimCorniereInegaleAcier.append([20.6,140,90,12,11,5.5,26.3,4.66,2.19,9.47,6.89,3.79,4.79,2.39,"M27",52,93,22.7,"M24",52,51,23.2,0.451,21.83,518.1,55.5,4.44,168.4,24.72,2.53,587.6,4.73,98.93,1.94,-170.6,22.15])
    dimCorniereInegaleAcier.append([23.8,140,90,14,11,5.5,30.4,4.74,2.27,9.43,6.92,3.88,4.78,2.45,"M27",54,93,26.2,"M24",54,51,26.7,0.451,18.9,591.9,63.96,4.41,191.3,28.41,2.51,670,4.7,113.3,1.93,-193.3,21.99])
    dimCorniereInegaleAcier.append([18.2,150,90,10,12,6,23.2,5,2.04,10.1,7.07,3.61,4.97,2.2,"M27",50,102,20.2,"M24",47,49,20.6,0.47,25.84,533.1,53.29,4.8,146.1,20.98,2.51,591.3,5.05,87.93,1.95,-160.9,19.87])
    dimCorniereInegaleAcier.append([19.9,150,90,11,12,6,25.3,5.04,2.08,10.07,7.09,3.66,4.95,2.23,"M27",51,102,22,"M24",48,49,22.5,0.47,23.61,580.7,58.3,4.79,158.7,22.91,2.5,643.7,5.04,95.7,1.94,-174.7,19.81])
    dimCorniereInegaleAcier.append([21.6,150,90,12,12,6,27.5,5.08,2.12,10.05,7.11,3.71,4.94,2.26,"M27",52,102,23.9,"M24",48,49,24.4,0.47,21.75,627.3,63.25,4.77,170.9,24.82,2.49,694.8,5.03,103.4,1.94,-188.1,19.75])
    dimCorniereInegaleAcier.append([19,150,100,10,12,6,24.2,4.81,2.34,10.27,7.48,4.08,5.25,2.64,"M27",50,102,21.2,"M24",47,58,21.6,0.49,25.83,552.6,54.23,4.78,198.5,25.92,2.87,637.3,5.14,113.8,2.17,-192.8,23.72])
    dimCorniereInegaleAcier.append([22.5,150,100,12,12,6,28.7,4.9,2.42,10.23,7.52,4.18,5.23,2.7,"M27",52,102,25.1,"M24",49,58,25.6,0.49,21.72,650.5,64.38,4.76,232.6,30.69,2.85,749.3,5.11,133.9,2.16,-225.9,23.61])
    dimCorniereInegaleAcier.append([26.1,150,100,14,12,6,33.2,4.98,2.5,10.19,7.55,4.28,5.22,2.75,"M27",54,102,29,"M24",51,58,29.6,0.49,18.79,744.4,74.27,4.74,264.9,35.32,2.82,855.9,5.08,153.4,2.15,-256.8,23.48])
    dimCorniereInegaleAcier.append([23,200,100,10,15,7.5,29.2,6.93,2.01,13.15,8.74,3.72,5.94,2.09,"M27",54,150,26.2,"M24",48,57,26.6,0.587,25.58,1219,93.24,6.46,210.3,26.33,2.68,1294,6.65,134.5,2.14,-286.8,14.82])
    dimCorniereInegaleAcier.append([27.3,200,100,12,15,7.5,34.8,7.03,2.1,13.08,8.81,3.82,5.89,2.17,"M27",54,150,31.2,"M24",50,57,31.7,0.587,21.49,1440,111,6.43,247.2,31.28,2.67,1529,6.63,158.5,2.13,-337.3,14.74])
    dimCorniereInegaleAcier.append([31.6,200,100,14,15,7.5,40.3,7.12,2.18,13.01,8.86,3.91,5.85,2.24,"M27",55,151,36.1,"M24",50,57,37.2,0.587,18.57,1654,128.4,6.41,282.2,36.08,2.65,1755,6.6,181.7,2.12,-384.8,14.65])
    dimCorniereInegaleAcier.append([33.7,200,100,15,15,7.5,43,7.16,2.22,12.98,8.89,3.95,5.84,2.27,"M27",56,151,38.5,"M24",50,57,39.9,0.587,17.4,1758,137,6.4,299.1,38.44,2.64,1865,6.59,193.1,2.12,-407.4,14.59])
    dimCorniereInegaleAcier.append([35.9,200,100,16,15,7.5,45.7,7.2,2.26,12.95,8.92,3.99,5.82,2.31,"M27",58,151,40.9,"M24",51,57,42.6,0.587,16.37,1861,145.4,6.38,315.6,40.76,2.63,1972,6.57,204.3,211,-429.3,14.53])
    dimCorniereInegaleAcier.append([1.12,30,20,3,4,2,1.43,0,0,0,0,0,0,0,0,0,0,0,0,0,0,0,0,0,0,0,0,0,0,0,0,0,0,0,0,0])
    dimCorniereInegaleAcier.append([1.43,35,20,3.5,4,2,1.82,0,0,0,0,0,0,0,0,0,0,0,0,0,0,0,0,0,0,0,0,0,0,0,0,0,0,0,0,0])
    dimCorniereInegaleAcier.append([1.73,40,20,3,4,2,1.36,0,0,0,0,0,0,0,0,0,0,0,0,0,0,0,0,0,0,0,0,0,0,0,0,0,0,0,0,0])
    dimCorniereInegaleAcier.append([2.46,40,25,4,4,2,1.93,0,0,0,0,0,0,0,0,0,0,0,0,0,0,0,0,0,0,0,0,0,0,0,0,0,0,0,0,0])
    dimCorniereInegaleAcier.append([2.24,45,30,4,4,2,2.86,0,0,0,0,0,0,0,0,0,0,0,0,0,0,0,0,0,0,0,0,0,0,0,0,0,0,0,0,0])
    dimCorniereInegaleAcier.append([2.76,45,30,5,4,2,3.52,0,0,0,0,0,0,0,0,0,0,0,0,0,0,0,0,0,0,0,0,0,0,0,0,0,0,0,0,0])
    dimCorniereInegaleAcier.append([2.96,50,30,5,5,2.5,3.78,0,0,0,0,0,0,0,0,0,0,0,0,0,0,0,0,0,0,0,0,0,0,0,0,0,0,0,0,0])
    dimCorniereInegaleAcier.append([3.76,60,40,5,6,3,4.79,0,0,0,0,0,0,0,0,0,0,0,0,0,0,0,0,0,0,0,0,0,0,0,0,0,0,0,0,0])
    dimCorniereInegaleAcier.append([4.46,60,40,6,6,3,5.68,0,0,0,0,0,0,0,0,0,0,0,0,0,0,0,0,0,0,0,0,0,0,0,0,0,0,0,0,0])
    dimCorniereInegaleAcier.append([5.14,60,40,7,6,3,6.55,0,0,0,0,0,0,0,0,0,0,0,0,0,0,0,0,0,0,0,0,0,0,0,0,0,0,0,0,0])
    dimCorniereInegaleAcier.append([5.4,70,50,6,6,3,6.88,0,0,0,0,0,0,0,0,0,0,0,0,0,0,0,0,0,0,0,0,0,0,0,0,0,0,0,0,0])
    dimCorniereInegaleAcier.append([7.36,80,60,7,8,4,9.38,0,0,0,0,0,0,0,0,0,0,0,0,0,0,0,0,0,0,0,0,0,0,0,0,0,0,0,0,0])
    dimCorniereInegaleAcier.append([9.6,90,70,8,8,4,12.23,0,0,0,0,0,0,0,0,0,0,0,0,0,0,0,0,0,0,0,0,0,0,0,0,0,0,0,0,0])
    dimCorniereInegaleAcier.append([8.99,100,50,8,9,4.5,11.4,0,0,0,0,0,0,0,0,0,0,0,0,0,0,0,0,0,0,0,0,0,0,0,0,0,0,0,0,0])
    dimCorniereInegaleAcier.append([11.79,100,75,9,10,5,15.03,0,0,0,0,0,0,0,0,0,0,0,0,0,0,0,0,0,0,0,0,0,0,0,0,0,0,0,0,0])
    dimCorniereInegaleAcier.append([15,120,80,10,11,5.5,19.1,0,0,0,0,0,0,0,0,0,0,0,0,0,0,0,0,0,0,0,0,0,0,0,0,0,0,0,0,0])
    dimCorniereInegaleAcier.append([19.9,150,90,11,12,6,25.3,0,0,0,0,0,0,0,0,0,0,0,0,0,0,0,0,0,0,0,0,0,0,0,0,0,0,0,0,0])
    dimCorniereInegaleAcier.append([31.6,200,100,14,15,7.5,40.28,0,0,0,0,0,0,0,0,0,0,0,0,0,0,0,0,0,0,0,0,0,0,0,0,0,0,0,0,0])

    return dimCorniereInegaleAcier
        
def ProfPlat():
    
    dimPlat=[]
    #,Première ligne épaisseur,,,,,,,,,,,,,,,,,,,,
    #,Ensuite largeurs,,,,,,,,,,,,,,,,,,,,
    dimPlat.append([0,4,5,6,7,8,10,12,14,15,16,18,20,25,30,35,40,45,50,60])
    dimPlat.append([20,0.628,0.785,0.942,1.10,1.26,1.57,1.88,2.20,2.36,0,0,0,0,0,0,0,0,0,0])
    dimPlat.append([25,0.785,0.981,1.18,1.37,1.57,1.96,2.36,2.75,2.94,3.14,3.53,0,0,0,0,0,0,0,0])
    dimPlat.append([30,0.942,1.18,1.41,1.65,1.88,2.36,2.83,3.30,3.53,3.77,4.24,4.71,0,0,0,0,0,0,0])
    dimPlat.append([35,1.11,1.37,1.65,1.92,2.20,2.75,3.30,3.85,4.12,4.40,4.95,5.50,6.87,0,0,0,0,0,0])
    dimPlat.append([40,1.26,1.57,1.88,2.20,2.51,3.14,3.77,4.40,4.71,5.02,5.65,6.28,7.85,9.42,0,0,0,0,0])
    dimPlat.append([45,1.41,1.77,2.12,2.47,2.83,3.53,4.24,4.95,5.30,5.65,6.36,7.07,8.83,10.6,0,0,0,0,0])
    dimPlat.append([50,1.57,1.96,2.36,2.75,3.14,3.93,4.71,5.50,5.89,6.28,7.07,7.85,9.81,11.8,13.7,0,0,0,0])
    dimPlat.append([55,1.73,2.16,2.59,3.02,3.45,4.32,5.18,6.04,6.48,6.91,7.77,8.64,10.8,13,15.1,0,0,0,0])
    dimPlat.append([60,1.88,2.36,2.83,3.30,3.77,4.71,5.65,6.59,7.07,7.54,8.48,9.42,11.8,14.1,16.5,18.8,0,0,0])
    dimPlat.append([65,0.628,2.55,3.06,3.57,4.08,5.1,6.12,7.14,7.65,8.16,9.18,10.2,12.8,15.3,17.9,20.4,23,0,0])
    dimPlat.append([70,0,2.75,3.3,3.85,4.4,5.5,6.59,7.69,8.24,8.79,9.89,11,13.7,16.5,19.2,22.0,24.7,27.5,0])
    dimPlat.append([75,0,2.94,3.53,0,4.71,5.89,7.07,0,8.83,9.42,0,11.8,14.7,17.7,20.6,23.6,0,0,0])
    dimPlat.append([80,0,3.14,3.77,4.40,5.02,6.28,7.54,8.79,9.42,10.0,11.3,12.6,15.7,18.8,22.0,25.1,28.3,31.4,0])
    dimPlat.append([90,0,3.53,4.24,4.95,5.65,7.07,8.48,9.89,10.6,11.3,12.7,14.1,17.7,21.2,24.7,28.3,31.8,35.3,0])
    dimPlat.append([100,0,3.93,4.71,5.50,6.28,7.85,9.42,11.0,11.8,12.6,14.1,15.7,19.6,23.6,27.5,31.4,35.3,0,0])
    dimPlat.append([110,0,4.32,5.18,6.04,6.91,8.64,10.4,12.1,13,13.8,15.5,17.3,21.6,25.9,30.2,34.5,0,0,0])
    dimPlat.append([120,0,4.71,5.65,6.59,7.54,9.42,11.3,13.2,14.1,15.1,17.0,18.8,23.6,28.3,0,0,0,0,0])
    dimPlat.append([130,0,0,0,6.12,8.16,10.2,12.3,14.3,15.3,16.3,18.4,20.4,25.5,30.6,35.7,40.8,45.9,51,62.2])
    dimPlat.append([140,0,0,5.49,6.6,8.79,11,13.2,15.4,16.5,17.6,19.8,22,27.5,33,38.5,44,49.5,55,65.9])
    dimPlat.append([150,0,0,0,7.07,9.42,11.8,14.1,16.5,17.7,18.8,21.2,23.6,29.4,35.3,41.2,47.1,53,58.9,70.7])
    dimPlat.append([160,0,0,0,7.53,10.1,12.6,15.1,17.6,18.8,20.1,22.6,25.1,31.4,37.7,44,50.2,56.5,62.8,75.4])
    dimPlat.append([170,0,0,0,0,10.7,13.3,16,18.7,20,21.4,24,26.7,33.4,40,46.7,53.4,60.1,66.7,80.1])
    dimPlat.append([180,0,0,0,8.47,11.3,14.1,17,19.8,21.2,22.6,25.4,28.3,35.3,0,0,0,0,0,0])
    dimPlat.append([200,0,0,0,9.42,12.6,15.7,18.8,22,23.6,25.1,28.3,31.4,39.3,47.1,55,62.8,0,0,0])
    dimPlat.append([220,0,0,0,10.35,0,13.81,17.27,20.7,0,25.9,0,0,35.54,0,0,0,0,0,0])
    dimPlat.append([250,0,0,0,11.77,0,15.7,19.62,23.55,0,29.43,0,0,39.25,49.1,58.86,0,0,0,0])
    dimPlat.append([300,0,0,0,14.13,0,18.84,23.55,28.26,0,35.32,0,0,47.1,58.9,70.65,0,0,0,0])
    dimPlat.append([350,0,0,0,0,0,0,27.47,0,0,41.2,0,0,54.94,68.7,82.4,0,0,0,0])
    dimPlat.append([400,0,0,0,0,0,25.12,31.4,0,0,47.1,0,0,0,78.5,94.2,0,0,0,0])

    return dimPlat

def ProfCarre():
    
    dimCarre=[]
    #,,,Section,
    #,d,Poids,A,
    #,(mm),(Kg/m),cm²,
    dimCarre.append([6,0.28,0.36])
    dimCarre.append([8,0.5,0.64])
    dimCarre.append([10,0.78,1])
    dimCarre.append([12,1.13,1.44])
    dimCarre.append([14,1.54,1.96])
    dimCarre.append([16,2,2.56])
    dimCarre.append([18,2.54,3.24])
    dimCarre.append([20,3.14,4])
    dimCarre.append([22,3.8,4.84])
    dimCarre.append([25,4.91,6.25])
    dimCarre.append([30,7.06,9])
    dimCarre.append([35,9.62,12.25])
    dimCarre.append([40,12.56,16])
    dimCarre.append([45,15.9,20.25])
    dimCarre.append([50,19.62,25])
    dimCarre.append([60,28.26,36])
    dimCarre.append([70,38.47,49])
    dimCarre.append([80,50.24,64])
    dimCarre.append([90,63.59,81])
    dimCarre.append([100,78.5,100])
    dimCarre.append([120,113.04,144])
    dimCarre.append([130,132.6,0])
    
    return dimCarre

def ProfTe():
    
    dimTe=[]
    #,,,,,,,,,Section,Surface,,
    #,b,h,e,e’,r1,r2,r3,Poids,A,peinture,,
    #,(mm),(mm),(mm),(mm),(mm),(mm),(mm),Kg/m,(cm²),m²/m,m²/t,
    dimTe.append([20,20,3,3,3,1.5,1,0.88,1.12,0.08,90.9])
    dimTe.append([25,25,3.5,3.5,3.5,2,1,1.29,1.64,0.1,77.51])
    dimTe.append([30,30,4,4,4,2,1,1.77,2.26,0.12,64.5])
    dimTe.append([35,35,4.5,4.5,4.5,2.5,1,2.33,2.97,0.14,57.1])
    dimTe.append([40,40,5,5,5,2.5,1,2.96,3.77,0.16,51.7])
    dimTe.append([45,45,5.5,5.5,5.5,3,1.5,3.67,4.67,0.18,46.6])
    dimTe.append([50,50,6,6,6,3,1.5,4.44,5.66,0.2,43])
    dimTe.append([60,60,7,7,7,3.5,2,6.23,7.94,0.24,36.8])
    dimTe.append([70,70,8,8,8,4,2,8.32,10.6,0.28,32.2])
    dimTe.append([80,80,9,9,9,4.5,2,10.7,13.6,0.32,28.7])
    dimTe.append([100,100,11,11,11,5.5,3,16.4,20.9,0.4,23.4])
    dimTe.append([30,35,4,4,4,2,1,1.94,2.48,0.13,67])
    dimTe.append([35,40,4.5,4.5,4,2,1,2.49,3.18,0.15,60.4])
    dimTe.append([40,45,5,5,5,2.5,1.5,3.14,4.01,0.17,54.1])
    
    return dimTe

def ProfRond():
    
    dimRond=[]
    #,G,d,A,
    #,,,mm²,
    #,kg/m,mm,X10²,
    dimRond.append([0.617,10,0.785])
    dimRond.append([0.888,12,1.13])
    dimRond.append([1.21,14,1.54])
    dimRond.append([1.39,15,1.77])
    dimRond.append([1.58,16,2.01])
    dimRond.append([1.78,17,2.27])
    dimRond.append([2,18,2.54])
    dimRond.append([2.23,19,2.84])
    dimRond.append([2.47,20,3.14])
    dimRond.append([2.98,22,3.8])
    dimRond.append([3.05,22.25,3.89])
    dimRond.append([3.43,23.6,4.37])
    dimRond.append([3.55,24,4.52])
    dimRond.append([3.7,245,4.71])
    dimRond.append([3.85,25,4.91])
    dimRond.append([4.17,26,5.31])
    dimRond.append([4.4,26.7,5.6])
    dimRond.append([4.49,27,5.73])
    dimRond.append([4.83,28,6.16])
    dimRond.append([5.19,29,6.61])
    dimRond.append([5.37,29.5,6.83])
    dimRond.append([5.44,29.7,6.93])
    dimRond.append([5.55,30,7.07])
    dimRond.append([5.92,31,7.55])
    dimRond.append([6.31,32,8.04])
    dimRond.append([7.13,34,9.08])
    dimRond.append([7.3,34.4,9.29])
    dimRond.append([7.55,35,9.62])
    dimRond.append([7.86,35.7,10])
    dimRond.append([7.99,36,10.2])
    dimRond.append([8.44,37,10.8])
    dimRond.append([8.9,38,11.3])
    dimRond.append([9.38,39,11.9])
    dimRond.append([9.47,39.2,12.1])
    dimRond.append([9.86,40,12.6])
    dimRond.append([10.9,42,13.9])
    dimRond.append([11.9,44,15.2])
    dimRond.append([12.5,45,15.9])
    dimRond.append([13,46,16.6])
    dimRond.append([13.6,47,17.3])
    dimRond.append([14.2,48,18.1])
    dimRond.append([14.9,49.2,19])
    dimRond.append([15.4,50,19.6])
    dimRond.append([16,51,20.4])
    dimRond.append([16.7,52,21.2])
    dimRond.append([17.3,53,22.1])
    dimRond.append([18,54,22.9])
    dimRond.append([18.7,55,23.8])
    dimRond.append([19.2,55.8,24.5])
    dimRond.append([19.3,56,24.6])
    dimRond.append([20,57,25.5])
    dimRond.append([20.7,58,26.4])
    dimRond.append([21.5,59,27.3])
    dimRond.append([22.2,60,28.3])
    dimRond.append([23.7,62,30.2])
    dimRond.append([24.5,63,31.2])
    dimRond.append([26,65,33.2])
    dimRond.append([30.2,70,38.5])
    dimRond.append([34.7,75,44.2])
    dimRond.append([39.5,80,50.3])
    dimRond.append([44.5,85,56.7])
    dimRond.append([49.9,90,63.6])
    dimRond.append([55.6,95,70.9])
    dimRond.append([61.7,100,78.5])
    dimRond.append([68,105,86.6])
    dimRond.append([74.6,110,95])
    
    return dimRond

def ProfTubeRond():
    
    dimTubeRond=[]
    
    Den11=u"TUBES GAZ SOUDÉS SÉRIE LÉGÈRE DITS «TARIF 1 et 2»"
    Den12=u"Norme de référence : NF EN 10255 (e NF A 49-145)"
    Den13=u"Nuance : S195T"
    #,DIAMÈTRE ,ÉPAISSEUR ,MASSE LINÉIQUE ,MASSE LINÉIQUE ,,
    #,,,Tubes noirs lisses ,Tubes galva lisses,,
    #,mm,mm,kg/m,kg/m,,
    dimTubeRond.append([13.5,2,0.57,0.59,1])
    dimTubeRond.append([17.2,2,0.75,0.78,1])
    dimTubeRond.append([21.3,2.3,1.08,1.12,1])
    dimTubeRond.append([26.9,2.3,1.40,1.46,1])
    dimTubeRond.append([33.7,2.9,2.20,2.29,1])
    dimTubeRond.append([42.4,2.9,2.82,2.93,1])
    dimTubeRond.append([48.3,2.9,3.25,3.38,1])
    dimTubeRond.append([60.3,3.2,4.51,4.69,1])
    dimTubeRond.append([70.0,3.2,5.27,5.48,1])
    dimTubeRond.append([76.1,3.2,5.75,5.98,1])
    dimTubeRond.append([88.9,3.2,6.76,7.03,1])
    dimTubeRond.append([101.6,3.6,8.70,9.05,1])
    dimTubeRond.append([114.3,3.6,9.83,10.22,1])
    dimTubeRond.append([139.7,4.5,15.00,15.60,1])
    dimTubeRond.append([165.1,4.5,17.80,18.51,1])
    Den21=u"TUBES GAZ SOUDÉS SÉRIE MOYENNE"
    Den22=u"Norme de référence : NF EN 10255 (ex 49-145)"
    Den23=u"Nuance : S195T "
    #,DIAMÈTRE ,ÉPAISSEUR ,MASSE LINÉIQUE ,MASSE LINÉIQUE ,,
    #,,,Tubes noirs lisses ,Tubes galva lisses,,
    #,mm,mm,kg/m,kg/m,,
    dimTubeRond.append([17.2,2.3,0.85,0.88,2])
    dimTubeRond.append([21.3,2.6,1.2,1.25,2])
    dimTubeRond.append([26.9,2.6,1.56,1.62,2])
    dimTubeRond.append([33.7,3.2,2.41,2.51,2])
    dimTubeRond.append([42.4,3.2,3.09,3.21,2])
    dimTubeRond.append([48.3,3.2,3.56,3.7,2])
    dimTubeRond.append([60.3,3.6,5.03,5.23,2])
    dimTubeRond.append([70,3.6,5.9,6.14,2])
    dimTubeRond.append([76.1,3.6,6.44,6.7,2])
    dimTubeRond.append([88.9,4,8.38,8.72,2])
    dimTubeRond.append([101.6,4,9.63,10.02,2])
    dimTubeRond.append([114.3,4.5,12.2,12.69,2])
    dimTubeRond.append([139.7,4.85,15,15.6,2])
    dimTubeRond.append([165.1,4.85,17.8,18.51,2])
    Den31=u"TUBES SANS SOUDURE DITS «TARIF 3»"
    Den32=u"Norme de référence : NF EN 10255-S (ex NF A 49-115)"
    Den33=u"Nuance : S195T"
    #,DIAMÈTRE ,ÉPAISSEUR ,MASSE LINÉIQUE ,MASSE LINÉIQUE ,,
    #,,,Tubes noirs lisses ,Tubes galva lisses,,
    #,mm,mm,kg/m,kg/m,,
    dimTubeRond.append([13.5,2.3,0.635,0.639,3])
    dimTubeRond.append([17.2,2.3,0.845,0.851,3])
    dimTubeRond.append([21.3,2.6,1.2,1.21,3])
    dimTubeRond.append([26.9,2.6,1.56,1.57,3])
    dimTubeRond.append([33.7,3.2,2.41,2.43,3])
    dimTubeRond.append([42.4,3.2,3.09,3.12,3])
    dimTubeRond.append([48.3,3.2,3.56,3.6,3])
    dimTubeRond.append([60.3,3.6,5.03,5.1,3])
    dimTubeRond.append([70,3.6,5.9,6.01,3])
    dimTubeRond.append([76.1,3.6,6.44,6.56,3])
    dimTubeRond.append([88.9,4,8.38,8.55,3])
    dimTubeRond.append([101.6,4,9.63,9.81,3])
    dimTubeRond.append([114.3,4.5,12.2,12.5,3])
    dimTubeRond.append([139.7,4.5,15,15.5,3])
    dimTubeRond.append([165.1,4.5,17.8,18.4,3])
    Den41=u"TUBES SANS SOUDURE POUR CANALISATIONS DITS «TARIF 10»"
    Den42=u"Norme de référence : NF EN 10216-1 (ex NF A 49-112)"
    Den43=u"Nuance courante : P235"
    #,DIAMÈTRE ,ÉPAISSEUR ,MASSE LINÉIQUE 
    #,mm,mm,kg/m
    dimTubeRond.append([21.3,2.00,0.952,0,4])
    dimTubeRond.append([26.9,2.30,1.40,0,4])
    dimTubeRond.append([33.7,2.30,1.78,0,4])
    dimTubeRond.append([38,2.60,2.27,0,4])
    dimTubeRond.append([42.4,2.60,2.55,0,4])
    dimTubeRond.append([44.5,2.60,2.69,0,4])
    dimTubeRond.append([48.3,2.60,2.93,0,4])
    dimTubeRond.append([54,2.60,3.30,0,4])
    dimTubeRond.append([57,2.90,3.87,0,4])
    dimTubeRond.append([60.3,2.90,4.11,0,4])
    dimTubeRond.append([70,2.90,4.80,0,4])
    dimTubeRond.append([76.1,2.90,5.24,0,4])
    dimTubeRond.append([88.9,3.20,6.76,0,4])
    dimTubeRond.append([101.6,3.60,8.70,0,4])
    dimTubeRond.append([108,3.60,9.27,0,4])
    dimTubeRond.append([114.3,3.60,9.83,0,4])
    dimTubeRond.append([133,4.00,12.70,0,4])
    dimTubeRond.append([139.7,4.00,13.40,0,4])
    dimTubeRond.append([159,4.50,17.10,0,4])
    dimTubeRond.append([168.3,4.50,18.20,0,4])
    dimTubeRond.append([193.7,5.60,25.10,0,4])
    dimTubeRond.append([219.1,6.35,33.10,0,4])
    dimTubeRond.append([244.5,6.30,37.00,0,4])
    dimTubeRond.append([273,6.35,41.10,0,4])
    dimTubeRond.append([323.9,7.10,55.50,0,4])
    dimTubeRond.append([355.6,8.00,68.60,0,4])
    dimTubeRond.append([406.4,8.80,86.30,0,4])
    dimTubeRond.append([419,10.00,101.00,0,4])
    Den51=u"TUBES SOUDÉS DITS «TARIF 19»"
    Den52=u"Norme de référence : NF EN 10217-1 (ex NF A 49-141)"
    Den53=u"Nuance : P235 TR1"
    #,DIAMÈTRE ,ÉPAISSEUR ,MASSE LINÉIQUE 
    #,mm,mm,kg/m
    dimTubeRond.append([60.3,2.9,4.11,0,5])
    dimTubeRond.append([70,2.9,4.80,0,5])
    dimTubeRond.append([76.1,2.9,5.24,0,5])
    dimTubeRond.append([88.9,3.2,6.76,0,5])
    dimTubeRond.append([101.6,3.6,8.70,0,5])
    dimTubeRond.append([108,3.6,9.27,0,5])
    dimTubeRond.append([114.3,3.6,9.83,0,5])
    dimTubeRond.append([133,4,12.70,0,5])
    dimTubeRond.append([139.7,4,13.40,0,5])
    dimTubeRond.append([159,4.5,17.10,0,5])
    dimTubeRond.append([168.3,4.5,18.20,0,5])
    Den61=u"TUBES SOUDÉS DE PRÉCISION NON DÉCALAMINÉS"
    Den62=u"Norme de référence : NF EN 10305-3 (ex XPA 49-646)"
    Den63=u"Nuance courante : E220CR2 État de surface : S1 (non décalaminé)"
    #,DIAMÈTRE ,ÉPAISSEUR ,MASSE LINÉIQUE 
    #,mm,mm,kg/m
    dimTubeRond.append([25,1.5,0.869,0,6])
    dimTubeRond.append([30,1.5,1.05,0,6])
    dimTubeRond.append([35,1.5,1.24,0,6])
    dimTubeRond.append([38,1.5,1.35,0,6])
    dimTubeRond.append([40,1.5,1.42,0,6])
    dimTubeRond.append([45,1.5,1.61,0,6])
    dimTubeRond.append([50,1.5,1.79,0,6])
    dimTubeRond.append([60,1.5,2.16,0,6])
    dimTubeRond.append([70,1.5,2.53,0,6])
    
    Deno=[Den11,Den12,Den13,Den21,Den22,Den23,Den31,Den32,Den33,Den41,Den42,Den43,Den51,Den52,Den53,Den61,Den62,Den63]
    
    return dimTubeRond,Deno
        
#
#    Recherche caractéristique sections
#

def ParamIouH(FaceSection):
    
    Section=FaceSection[1]
    
    CDG=Section.Faces[0].CenterOfMass
    
    ln=Ln(Section.Faces[0].Edges)
        
    edge1=Section.Faces[0].Edges[ln[0][0]]
    edge2=Section.Faces[0].Edges[ln[2][0]]

    C1=centerLinePoint(edge1,0)
    C2=centerLinePoint(edge2,0)
    d1=C1.sub(CDG)
    d2=C2.sub(CDG)
    l1=math.sqrt((d1.x)**2+(d1.y)**2+(d1.z)**2)
    l2=math.sqrt((d2.x)**2+(d2.y)**2+(d2.z)**2)

    if l1>l2:
        h=l1*2
        b=edge1.Length
        tw=l2*2
        Zaxe=edge1.tangentAt(0)
    else :
        h=l2*2
        b=edge2.Length
        tw=l1*2
        Zaxe=edge2.tangentAt(0)
    
    PtAxe=CDG
        
    return [h,b,tw,PtAxe,Zaxe]

def ParamCorniereAcier(FaceSection):
    
    Section=FaceSection[1]
    
    ln=Ln(Section.Faces[0].Edges)
            
    edge0=Section.Faces[0].Edges[ln[0][0]]
    edge2=Section.Faces[0].Edges[ln[2][0]]
    edge3=Section.Faces[0].Edges[ln[3][0]]
        
    if ln[0][1]-ln[1][1]<tolerance:
        L1=edge0.Length
        L2=L1
    else:
        edge1=Section.Faces[0].Edges[ln[1][0]]
        L1=edge0.Length
        L2=edge1.Length
    
    Vector_A = edge0.valueAt( 0.0 )
    Vector_B = edge0.valueAt( edge0.Length )
    Vector_C20 = edge2.valueAt( 0.0 )
    Vector_C21 = edge2.valueAt( edge2.Length )
    Vector_C30 = edge3.valueAt( 0.0 )
    Vector_C31 = edge3.valueAt( edge3.Length )
    
    Vector_T, Ep20, Vector_Tprime = intersecPerpendicularLine(Vector_A, Vector_B, Vector_C20, info=0)
    Vector_T, Ep21, Vector_Tprime = intersecPerpendicularLine(Vector_A, Vector_B, Vector_C21, info=0)
    Vector_T, Ep30, Vector_Tprime = intersecPerpendicularLine(Vector_A, Vector_B, Vector_C30, info=0)
    Vector_T, Ep31, Vector_Tprime = intersecPerpendicularLine(Vector_A, Vector_B, Vector_C31, info=0)
    
    Eps=[Ep20,Ep21,Ep30,Ep31]
    
    Eps.sort(None,None,False)
    Ep=Eps[0]
    if Eps[0]-Eps[1]>tolerance:
        "Problème"
    
    CDG=Section.Faces[0].CenterOfMass
    
    PtAxe=CDG
    
    ZAxe=Vector_A
    
    return [L1,L2,Ep,PtAxe,ZAxe]
    

def ParamPlatCarre(FaceSection):
    
    Section=FaceSection[1]
    
    ln=Ln(Section.Faces[0].Edges)
    
    edge0=Section.Faces[0].Edges[ln[0][0]]
    edge2=Section.Faces[0].Edges[ln[2][0]]
    
    CDG=Section.Faces[0].CenterOfMass
    
    L1=edge0.Length
    L2=edge2.Length
    
    if L1==L2:
        Type=u"Carré"
        
    if L1>L2:
        Type=u"Rectangle"
    else:
        t1=L2
        t2=L1
        L1=t1
        L2=t2
        
    PtAxe=CDG
    
    ZAxe=edge0.tangentAt(0)
            
    return [L1,L2,Type,PtAxe,ZAxe]
        
def ParamTe(FaceSection):
    
    Section=FaceSection[1]
    
    ln=Ln(Section.Faces[0].Edges)
    lninv=ln[:]
    lninv.sort(cmp=compinv)
        
    edge0=Section.Faces[0].Edges[ln[0][0]]
    edge1=Section.Faces[0].Edges[ln[1][0]]
    edge2=Section.Faces[0].Edges[ln[2][0]]
    
    edgePlusPetite=Section.Faces[0].Edges[lninv[0][0]]
    
    CDG=Section.Faces[0].CenterOfMass
    
    L0=edge0.Length
    L1=edge1.Length
    L2=edge2.Length
    b=0
    h=0
    
    if abs(L1-L2)<=tolerance:
        b=L0
        C1=centerLinePoint(edge0,0)
        C2=centerLinePoint(edgePlusPetite,0)
        d1=C1.sub(C2)
        h=math.sqrt((d1.x)**2+(d1.y)**2+(d1.z)**2)
    
    if abs(L0-L1)<=tolerance:
        b=L2
        C1=centerLinePoint(edge2,0)
        C2=centerLinePoint(edgePlusPetite,0)
        d1=C1.sub(C2)
        h=math.sqrt((d1.x)**2+(d1.y)**2+(d1.z)**2)
    
    ZAxe=d1.tangentAt(0)
    
    PtAxe=CDG
    
    return [b,h,PtAxe,ZAxe]

def ParamRond(FaceSection):
    
    Section=FaceSection[1]
    
    edge=Section.Faces[0].Edges[0]
    
    d=edge.Length/(2*math.pi)    
    
    CDG=Section.Faces[0].CenterOfMass
    PtAxe=CDG
    
    P0=edge.Curve.Center
    P1=edge.valueAt(edge.FirstParameter)
    ZAxe=P1-P0
    
    return [d,PtAxe,ZAxe]

def ParamTubeRond(FaceSection):
    
    Section=FaceSection[1]
    
    ln=LnCurves(Section.Faces[0].Edges)

    edge1=Section.Faces[0].Edges[ln[0][0]]
    
    if len(ln)==2:
        edge2=Section.Faces[0].Edges[ln[1][0]]
        
    elif len(ln)==4:
        edge2=Section.Faces[0].Edges[ln[3][0]]
        
    d1=2*edge1.Curve.Radius
    d2=2*edge2.Curve.Radius
    ep=(d1-d2)/2
        
    #~ print d1,d2,ep
    
    CDG=Section.Faces[0].CenterOfMass
    PtAxe=CDG
    
    P0=edge1.Curve.Center
    P1=edge1.valueAt(edge1.FirstParameter)
    ZAxe=P1-P0
    
    return [d1,d2,ep,PtAxe,ZAxe]

def ParamTubeCarreRectangle(FaceSection):
    
    Section=FaceSection[1]
    
    ln=Ln(Section.Faces[0].Edges)
    
    #Recherche de toutes les longueurs d'arrête différentes
    L=ln[0][1]
    nbLdiff=[ln[0][0]]
    for ed in ln:
        if abs(ed[1]-L)>=tolerance:
            nbLdiff.append(ed[0])
        L=ed[1]
    #~ print nbLdiff
    ListeCotes=[]
    for EdPr in nbLdiff:
        V1=Section.Faces[0].Edges[EdPr].tangentAt(0.0)
        C1=centerLinePoint(Section.Faces[0].Edges[EdPr],0)
        Lmax=0.0
        for ed in ln:
            V2=Section.Faces[0].Edges[ed[0]].tangentAt(0.0)
            if ed[0]!= EdPr and abs(V1.x)-abs(V2.x)<=tolerance and abs(V1.y)-abs(V2.y)<=tolerance and abs(V1.z)-abs(V2.z)<=tolerance :
                C2=centerLinePoint(Section.Faces[0].Edges[ed[0]],0)
                d=C1.sub(C2)
                l=d.Length
                if l>Lmax :
                    Lmax=l
                    nmax=ed[0]
        V1=Section.Faces[0].Edges[nmax].tangentAt(0.0)
        C1=centerLinePoint(Section.Faces[0].Edges[nmax],0)
        CoteEdPr=[]
        for ed in ln:
            V2=Section.Faces[0].Edges[ed[0]].tangentAt(0.0)
            if ed[0]!= nmax and abs(V1.x)-abs(V2.x)<=tolerance and abs(V1.y)-abs(V2.y)<=tolerance and abs(V1.z)-abs(V2.z)<=tolerance :
                C2=centerLinePoint(Section.Faces[0].Edges[ed[0]],0)
                d=C1.sub(C2)
                l=d.Length
                CoteEdPr.append(l)
        ListeCotes.append(CoteEdPr)
    
    if len(ListeCotes)==2:
        b=max(ListeCotes[1])
    else:
        b=max(ListeCotes[0])
    h=max(ListeCotes[0])
    ep=min(ListeCotes[0])
    
    CDG=Section.Faces[0].CenterOfMass
    PtAxe=CDG
    
    ZAxe=Section.Faces[0].Edges[ln[0][0]].tangentAt(0)
    
    return [h,b,ep,PtAxe,ZAxe]

def ParamTubeCarreRectangleAlu(FaceSection):
    
    Section=FaceSection[1]
    
    ln=Ln(Section.Faces[0].Edges)
    #~ print u"ln"
    #~ print ln
    #~ print u"------"
    edge1=Section.Faces[0].Edges[ln[0][0]]
    
    Part.show(edge1)
    
    edge10X=edge1.Vertexes[0].X
    edge10Y=edge1.Vertexes[0].Y
    edge10Z=edge1.Vertexes[0].Z
    edge11X=edge1.Vertexes[1].X
    edge11Y=edge1.Vertexes[1].Y
    edge11Z=edge1.Vertexes[1].Z

    h=edge1.Length
    cpt=0
    n=4
    for ed in Section.Faces[0].Edges:
        
        edX=ed.Vertexes[0].X
        edY=ed.Vertexes[0].Y
        edZ=ed.Vertexes[0].Z
        
        #~ print u"--------------"
        #~ print edX
        #~ print edge10X
        #~ print edge11X
        #~ print edY
        #~ print edge10Y
        #~ print edge11Y
        #~ print edZ
        #~ print edge10Z
        #~ print edge11Z
        #~ print u"--------------"
        #~ print abs(edX-edge10X)
        #~ print abs(edY-edge10Y)
        #~ print abs(edZ-edge10Z)
        #~ print u"***********"
        #~ print abs(edX-edge10X)
        #~ print abs(edY-edge10Y)
        #~ print abs(edZ-edge10Z)
        #~ print u"***********"
        #~ 
        
        if cpt!=ln[0][0]:
            if abs(edX-edge10X)<=tolerance and abs(edY-edge10Y)<=tolerance and abs(edZ-edge10Z)<=tolerance :
                print u"Why?"
                b=ed.Length
            if abs(edX-edge11X)<=tolerance and abs(edY-edge11Y)<=tolerance and abs(edZ-edge11Z)<=tolerance :
                b=ed.Length
        cpt=cpt+1
        
    L=Section.Faces[0].Wires[0].Length
    cpt=0
    for wire in Section.Faces[0].Wires:
        if L-wire.Length>=tolerance:
            L=wire.Length
            n=cpt
        cpt=cpt+1
    
    C0=centerLinePoint(edge1,0)
    C1=centerLinePoint(Section.Faces[0].Wires[n].Edges[0])
    dmin=C0.sub(C1).Length
    
    for edge in Section.Faces[0].Wires[n].Edges:
        Cx=centerLinePoint(edge,0)
        dist=C0.sub(Cx).Length
        if dist-dmin<=tolerance:
            dmin=dist
    
    ep=dmin
    
    CDG=Section.Faces[0].CenterOfMass
    PtAxe=CDG
    
    ZAxe=edge1.tangentAt(0)
    
    return [h,b,ep,PtAxe,ZAxe]


def ParamUPE(FaceSection):
    
    Section=FaceSection[1]
    
    ln=Ln(Section.Faces[0].Edges)
    
    #~ print ln
    
    h=ln[0][1]
    b=ln[2][1]
    tw=ln[len(ln)-1][1]
    
    CDG=Section.Faces[0].CenterOfMass
    PtAxe=CDG
    
    ZAxe=Section.Faces[0].Edges[ln[0][0]].tangentAt(0)
    
    return [h,b,tw,PtAxe,ZAxe]
    
def ParamUPN(FaceSection):
    
    Section=FaceSection[1]
    
    ln=Ln(Section.Faces[0].Edges)
    
    #~ print ln
    
    h=ln[0][1]
    b=ln[2][1]
    
    edge1=Section.Faces[0].Edges[ln[0][0]]
    edge2=Section.Faces[0].Edges[ln[1][0]]
    
    C1=centerLinePoint(edge1,0)
    C2=centerLinePoint(edge2,0)
    
    tw=C1.sub(C2).Length
    
    CDG=Section.Faces[0].CenterOfMass
    PtAxe=CDG
    
    ZAxe=Section.Faces[0].Edges[ln[0][0]].tangentAt(0)
    
    
    return [h,b,tw,PtAxe,ZAxe]
    
def ParamLAlu(FaceSection):
    
    Section=FaceSection[1]
    
    ln=Ln(Section.Faces[0].Edges)
    
    #~ print ln
    
    h=ln[0][1]
    
    edge1=Section.Faces[0].Edges[ln[0][0]]
    edge10X=edge1.Vertexes[0].X
    edge10Y=edge1.Vertexes[0].Y
    edge10Z=edge1.Vertexes[0].Z
    edge11X=edge1.Vertexes[1].X
    edge11Y=edge1.Vertexes[1].Y
    edge11Z=edge1.Vertexes[1].Z
    
    ListeArretEnContact=[]
    cpt=0
    
    for ed in Section.Faces[0].Edges:
        for vert in ed.Vertexes:
            edX=vert.X
            edY=vert.Y
            edZ=vert.Z
            if cpt!=ln[0][0]:
                if abs(edX-edge10X)<=tolerance and abs(edY-edge10Y)<=tolerance and abs(edZ-edge10Z)<=tolerance :
                    ListeArretEnContact.append([ed.Length,cpt])
                if abs(edX-edge11X)<=tolerance and abs(edY-edge11Y)<=tolerance and abs(edZ-edge11Z)<=tolerance :
                    ListeArretEnContact.append([ed.Length,cpt])
            cpt=cpt+1
    
    ListeArretEnContact.sort()
    
    b=ListeArretEnContact[1][0]
        
    ep=ListeArretEnContact[0][0]
    
    CDG=Section.Faces[0].CenterOfMass
    PtAxe=CDG
    
    ZAxe=edge1.tangentAt(0)
    
    return [h,b,ep,PtAxe,ZAxe]

def ParamUPAF(FaceSection):
    
    Section=FaceSection[1]
    
    ln=Ln(Section.Faces[0].Edges)
    
    edge=Section.Faces[0].Edges[ln[0][0]]
    
    h=10
    b=10
    ep=10
    
    CDG=Section.Faces[0].CenterOfMass
    PtAxe=CDG
    
    ZAxe=edge.tangentAt(0)
        
    return [h,b,ep,PtAxe,ZAxe]

def TypeSol(Solide):
    
    TypeSolide=1
    
    FacePlaque=0
    
    Label=Solide.Label
    
    faces=Solide.Shape.Faces
    edges=Solide.Shape.Edges
    
    TriFaces=Sn(faces)
    TriEdges=LnCurves(edges)
    #~ print TriEdges
    
    ListeEdgesBord=[]
    #~ print TriFaces[0][1]
    #~ print TriFaces[1][1]
    #~ print TriFaces[2][1]
    
    #Identification des suite de poutres (Tuyauterie)
    FacesTangentes=[]
    FaceNo1=faces[TriFaces[0][0]]
    EdgeOfFaceNo1=LnCurves(FaceNo1.Edges)
    EdgeNo1=FaceNo1.Edges[EdgeOfFaceNo1[0][0]]
    #~ Part.show(FaceNo1)
    #~ Part.show(EdgeNo1)
    #~ for face in faces:
        #~ for edge in face.Edges:
            #~ if edge.curvatureAt(0)==0.0:
                #~ print u"En travaux...."
            #~ else :
                #~ print u"trouvé"
        #~ 
        #~ print u"En travaux...."
    
    #Identification des plaques non pliées
    n=0
    if TriFaces[0][1]-TriFaces[1][1]<=0.1:#Essayer avec une plaque avec trous lamé, la plus petite possible pourvoir...
        if TriFaces[1][1]-TriFaces[2][1]>tolerance:
            v0=faces[TriFaces[0][0]].normalAt(0,0)
            for edge in edges:
                ve=edge.tangentAt(0)
                DeltaX=abs(v0.x)-abs(ve.x)
                DeltaY=abs(v0.y)-abs(ve.y)
                DeltaZ=abs(v0.z)-abs(ve.z)
                if DeltaX<tolerance and DeltaY<tolerance and DeltaZ<tolerance:
                    ListeEdgesBord.append(n)
                    #~ Part.show(edge)
                    #~ print ListeEdgesBord
                n=n+1
            NbEdFace1=len(Solide.Shape.Faces[TriFaces[0][0]].Edges)
            NbEdFace2=len(Solide.Shape.Faces[TriFaces[1][0]].Edges)
            NbEdBorddeCoupe=len(ListeEdgesBord)
            if NbEdFace1+NbEdFace2+NbEdBorddeCoupe==len(edges):
                TriEdgeGrdFace=LnCurves(Solide.Shape.Faces[TriFaces[0][0]].Edges)
                LMax=TriEdgeGrdFace[0][1]
                Area=Solide.Shape.Faces[TriFaces[0][0]].Area
                lmin=Area/LMax
                if LMax/lmin<20.0: #Critère pour savoir si on est sur un plat ou sur une plaque
                    TypeSolide=3
    
    return TypeSolide,Label,faces[TriFaces[1][0]],ListeEdgesBord,faces,edges,TriFaces,TriEdges

def GetSection(Sol,faces,edges,triFaces,triEdges):




    EdgesSol=edges
    FacesSol=faces
    Label=Sol.Label
    #---------------
    #Recherche de l'arrête la plus longue
    HighLength=0.0
    No=0
    n=0
    for edge in EdgesSol:
        if edge.Length>HighLength:
            HighLength=edge.Length
            No=n
        n=n+1
    #~ print HighLength
    #---------------
    #Création de plans normaux à l'arrête la plus longue et section avec le solide pour trouver la section
    #la plus grande donc celle qui est théoriquement complète... Laisse passer des erreurs
    #A améliorer en projetants toutes les faces normales...
    
    NbPLans = 3
    edgeHighLength=EdgesSol[No]
    
    #~ Part.show(edgeHighLength)
    
    SurfSect=0.0
    Param=edgeHighLength.LastParameter-edgeHighLength.FirstParameter
    PasParam=Param/NbPLans
    for n in range(NbPLans):
        n=n*1.0
        val=edgeHighLength.FirstParameter+n*PasParam
        PtCenter=edgeHighLength.valueAt(val)
        VectDir=edgeHighLength.tangentAt(val)
        PlaneCenter=Part.makePlane(HighLength*10,HighLength*10,PtCenter, VectDir )
        Plane_Center = PlaneCenter.CenterOfMass
        Plane_Translate =  PtCenter - Plane_Center
        PlaneCenter.translate( Plane_Translate )
        #~ Part.show(PlaneCenter)
        Sect=PlaneCenter.common(Sol.Shape)
        if Sect.Area-SurfSect>tolerance:
            SurfSect=Sect.Area
            Section=Sect
            #~ Part.show(Sect)
        n=n+1
    #~ Part.show(Section)
    #~ Part.show(PlaneCenter)
    #---------------
    #Recherche de toutes les arrêtes parallèles à la plus longue
    #ou ayant le même axe de rotation pour les profils courbés
    ###### 
    ParallelEdges=[]
    if EdgesSol[No].curvatureAt(0.0)<=tolerance:
        n=0
        VB=(EdgesSol[No].Curve.EndPoint -EdgesSol[No].Curve.StartPoint).normalize()
        for edge in EdgesSol:
            if edge.curvatureAt(0)==0.0:
                VA = (edge.Curve.EndPoint - edge.Curve.StartPoint).normalize()
                if abs((VA.cross(VB)).Length) <= tolerance:
                    ParallelEdges.append(edge)
                    #~ Part.show(EdgesSol[n])
            n=n+1    
    else :
        n=0
        Dir1=EdgesSol[No].Curve.Axis*HighLength
        Dir2=EdgesSol[No].Curve.Axis*(-HighLength)
        Pt=EdgesSol[No].Curve.Center
        Dir1=Pt+Dir1
        Dir2=Pt+Dir2
        Axe=Part.makeLine(Dir1,Dir2)
        for edge in EdgesSol:
            if edge.curvatureAt(0.0)>=tolerance:
                if edge.Curve.Center.distanceToLine(Dir1,Dir2)<=tolerance:
                    ParallelEdges.append(edge)
                    #~ Part.show(edge)
            n=n+1
        
        #Profil courbé
        #~ for ed in ParallelEdges:
        #~ Part.show(EdgesSol[ed])
    #---------------
    #Tri des faces du solide
    #Tri des faces normales par rapport à la section
    #~ vectFaceSect=Section.Faces[0].Surface#vecteur normale à la section
    #~ n=0
    #~ ListeFaceNormalSection=[]
    #~ for face in FacesSol:
        #~ if (str(face.Surface) == "<Plane object>")  :
            #~ vectFace=face.Surface.Axis
            #~ if math.degrees(vectFace.getAngle(vectFaceSect))==90:
                #~ Part.show(face)
                #~ ListeFaceNormalSection.append(n)
        #~ elif (str(face.Surface) == "<Cylinder object>"):
            #~ vectFace=face.Surface.Axis
            #~ if math.degrees(vectFace.getAngle(vectFaceSect))==0 or math.degrees(vectFace.getAngle(vectFaceSect))==180:
                #~ Part.show(face)
                #~ ListeFaceNormalSection.append(n)
        #~ n=n+1
    #Tri des faces coplanaire avec une des arrêtes de la section
    
    n=0
    ListeFaceCoplanEdgeSection=[]
    
    #~ for edge in Section.Edges:
        #~ for face in FacesSol:
            #~ if (str(face.Surface) == "<Plane object>")  :
                #~ d0=edge.Vertexes[0].distToShape(face.Surface)
                #~ d1=edge.Vertexes[1].distToShape(face.Surface)
                #~ if d0[0]<tolerance and d1[0]<tolerance:
                    #~ Part.show(face)
                #~ ListeFaceCoplanEdgeSection
            #~ elif (str(face.Surface) == "<Cylinder object>"):
                #~ print u"en cours"
            
            

            
            
            
            
            
    #---------------
    #Recherche des deux faces d'extrémitées
    ExtremFacesNo=[]
    ExtremFaces=[]
    VertexesHighEdge=EdgesSol[No].Vertexes
    n=0
    for face in FacesSol:
        nb=0
        for vertexe in VertexesHighEdge:
            if abs(vertexe.distToShape(face)[0])<=tolerance:
                nb=nb+1
        if nb==1:            
            ExtremFaces.append(face)
            ExtremFacesNo.append(n)
            #~ Part.show(FacesSol[n])
        n=n+1
    #~ for face in ExtremFaces:
        #~ Part.show(face)
    
    #---------------
    #Recherche de l'arrête la plus courte aboutissant sur une face d'extrémité
    #~ LowLength=[HighLength,0]
    #~ n=0
    #~ for edge in ParallelEdges:
        #~ for vertexe in EdgesSol[edge].Vertexes:
            #~ if abs(vertexe.distToShape(FacesSol[ExtremFacesNo[0]])[0])<=tolerance:
                #~ if EdgesSol[edge].Length <= LowLength[0]:
                    #~ LowLength[0]=EdgesSol[edge].Length
                    #~ LowLength[1]=n
        #~ n=n+1
    
    #~ Part.show(EdgesSol[ParallelEdges[LowLength[1]]])
    
    #---------------
    #Création d'un plan normal à la courbe précédement trouvée puis section en testant qu'il n'y a qu'une face.
    #si + de 1 face : présence de trous. Pas de test pour savoir si présence d'un usiange non traversant dans la
    #section.... reste à chercher (piste : toutes les faces coupé doivent donné un résultat unique...)
    #Encore une fois fortement inspiré de la macro WorkFeature
    
    #~ LowEdge=EdgesSol[ParallelEdges[LowLength[1]]]
    #~ V1=centerLinePoint(LowEdge,0)
    #~ Part.show(LowEdge)
    
    #~ Vector_A = LowEdge.valueAt( 0.0 )
    #~ Vector_B = LowEdge.valueAt( LowEdge.Length )
    #~ Vector_C = V1
    #~ 
    #~ Plane_Normal = Vector_B - Vector_A
    #~ 
    #~ Vector_T=Vector_C
    #~ 
    #~ Plane_Point = Vector_T +  (Vector_C - Vector_T).multiply(0.5)
            #~ 
    #~ Plane_face=Part.makePlane(HighLength*10,HighLength*10,Plane_Point, Plane_Normal )
    #~ 
    #~ Plane_Center = Plane_face.CenterOfMass
    #~ Plane_Translate =  Plane_Point - Plane_Center
    #~ Plane_face.translate( Plane_Translate )
    #~ Part.show(Plane_face)
    #~ plane.Shape = Plane_face
    #~ Part.show(Plane_face)

    #~ Section=Plane_face.common(Sol.Shape)
    #~ Part.show(Section)
    if len(Section.Faces)==1:
        TestBarre=True
    
    # Reste à implémanter le test de validation...
    
    
    
    
    
    
    
    
    
    
    
    return [Section,HighLength,TestBarre,ExtremFaces,Label,ParallelEdges,Sol]

def GetInfoPlaque(Pla,Face,EdgesEdge):
    
    Name=Pla.Label
    
    faces=Pla.Shape.Faces
    edges=Pla.Shape.Edges    
    L=[]
    LSomme=0.0
    for edge in EdgesEdge:
        #~ Part.show(edges[edge])
        l=edges[edge].Length
        L.append(l)
        LSomme=LSomme+l
    Lmoy=LSomme/len(L)
    #~ print Lmoy
    
    #Compte les trous...
    WireOfDecoupe=[] #Liste des wire des trous et des oblongs
    #on commence par enlever la wire du contour principale 
    AreaMax=0
    n=0
    for wire in Face.Wires:
        face=Part.Face(wire)
        if face.Area>AreaMax:
            AreaMax=face.Area
            WireExt=n
        n=n+1    
    n=0
    for wire in Face.Wires:
        if WireExt<>n:
            WireOfDecoupe.append(wire)
        n=n+1
    WireOfTrous=[]
    WireOfOblongs=[]
    for wire in WireOfDecoupe:
        cptLigne=0 #compteur d'arrête droite pour exclure tous les perçages plus compliqués que des trous oblongs.
        cptArc=0 #
        for edge in wire.Edges:
            #~ print edge.curvatureAt(0.0)
            if edge.curvatureAt(0.0)<=tolerance:
                cptLigne=cptLigne+1
            else:
                cptArc=cptArc+1
        #~ print u"cpt"
        #~ print cptLigne
        #~ print cptArc
        #~ print u"------"
        if cptArc==1 or cptArc ==2:
            if cptLigne==0:
                WireOfTrous.append(wire)
            else:
                WireOfOblongs.append(wire)
    Radius=[]
    
    if len(WireOfTrous)>0:
        for wire in WireOfTrous:
            #~ print wire.Edges[0].Curve.Radius
            #~ print wire.Edges[0].Curve.Center
            Radius.append(wire.Edges[0].Curve.Radius)
        Radius.sort(None,None,False)
        n=0
        Qt=1
        Holes=[]
        for r in Radius:
            
            if n!=0:
                if r==Radius[n-1]:
                    Qt=Qt+1
                else :
                    Holes.append([2*Radius[n-1],Qt])
                    Qt=1
                if n==len(Radius)-1:
                    Holes.append([2*r,Qt])
            n=n+1
    else:
        Holes=[]
            
    if len(WireOfOblongs)>0:
        RadiusAndCenterOblongs=[]
        for wire in WireOfOblongs:
            R=0
            for edge in wire.Edges:
                if edge.curvatureAt(0.0)>tolerance:
                    if R==0:
                        R=edge.Curve.Radius
                        Center=edge.Curve.Center
                    else:
                        if edge.Curve.Radius!=R:
                            R=0
                        else:
                            Center=Center-edge.Curve.Center
                            Dist=math.sqrt(math.pow(Center.x,2)+math.pow(Center.y,2)+math.pow(Center.z,2))
                            #~ print Dist
            if R!=0:
                RadiusAndCenterOblongs.append([R,Dist])
        RadiusAndCenterOblongs.sort(None,None,False)
        #~ print RadiusAndCenterOblongs
        OblonHoles=[[1,RadiusAndCenterOblongs[0][0],RadiusAndCenterOblongs[0][1]]]
        #~ print OblonHoles
        nbdiff=0
        for n in range(len(RadiusAndCenterOblongs)-1):
            if RadiusAndCenterOblongs[n+1][0]==RadiusAndCenterOblongs[n][0] and RadiusAndCenterOblongs[n+1][1]==RadiusAndCenterOblongs[n][1]:
                OblonHoles[nbdiff][0]=OblonHoles[nbdiff][0]+1
            else:
                OblonHoles.append([1,RadiusAndCenterOblongs[n+1][0],RadiusAndCenterOblongs[n+1][1]])
                nbdiff=nbdiff+1
            print u"------------"
            #~ print OblonHoles
    else:
        OblonHoles=[]
    
    FacePlaque=Face
    Thickness=Lmoy
    
    return FacePlaque,Name,Thickness,Holes,OblonHoles

    
def TypeSection(Section):
    
    NbEdge=len(Section.Edges)
    
    NbWires=len(Section.Wires)
    #si 2 profil fermé, si 1 profil ouvert
    
    LgDroites=[]
    for edge in Section.Edges:
        if edge.curvatureAt(0.0)<tolerance:
            LgDroites.append(edge.Length)
    NbDroite=len(LgDroites)
    LgDroites.sort()
    NbLgDiff=1
    if NbDroite >0:
        Lg=LgDroites[0]
        for n in LgDroites:
            if abs(n-Lg)>=tolerance:
                NbLgDiff=NbLgDiff+1
                Lg=n
        
    else:
        NbLgDiff=0
    #~ print NbLgDiff
        
    Type=[FamilleProfile(NbEdge,NbWires,NbDroite,NbLgDiff),Section]
    if Type[0]!= False:
        if Type[0][5]==1:
            Profil=ProfilIPEouHE(Type)    
        elif Type[0][5]==2:
            Profil=ProfilIPN(Type)    
        elif Type[0][5]==3:
            Profil=ProfilUPN(Type)    
        elif Type[0][5]==4:
            Profil=ProfilUPE(Type)    
        elif Type[0][5]==5:
            Profil=ProfilCorniere(Type)    
        elif Type[0][5]==6:
            Profil=ProfilPlatCarre(Type)    
        elif Type[0][5]==7:
            Profil=ProfilTe(Type)    
        elif Type[0][5]==8:
            Profil=ProfilRond(Type)    
        elif Type[0][5]==9:
            Profil=ProfilTubeRond(Type)    
        elif Type[0][5]==10:
            Profil=ProfilTubeCarreRectangle(Type)    
        elif Type[0][5]==11:
            Profil=ProfilLAlu(Type)    
        elif Type[0][5]==12:
            Profil=ProfilTouUAlu(Type)    
        elif Type[0][5]==13:
            Profil=ProfilTubeCarreRectangleAlu(Type)
        elif Type[0][5]==14:
            Profil=ProfilUPAFAcier(Type)    
    else:
        Profil=0
    #~ print Profil
    return Profil

def TraceAxeBArre(Section,ExtremFaces,PtAxe,LMax,parallelEdges):
    
    #~ Part.show(Section)
    #~ Part.show(ExtremFaces[0])
    #~ Part.show(ExtremFaces[1])
    #~ 
    #~ Draft.makePoint(PtAxe.x,PtAxe.y,PtAxe.z)
    face = Section.Faces[0]
    surf = Section.Faces[0].Surface
    V1=App.Vector(PtAxe.x,PtAxe.y,PtAxe.z)
    m_uv = surf.parameter(V1)
    u,v = m_uv[0], m_uv[1]
    m_p1 = face.valueAt(u,v)
    m_p2 = face.normalAt(u,v)
    if parallelEdges[0].curvatureAt(0.0)<=tolerance:
        m_p3 = m_p1 + m_p2.normalize().multiply(LMax)
        m_p4 = m_p1 + m_p2.normalize().multiply(-LMax)
        Courbe=Part.makeLine((m_p3.x,m_p3.y,m_p3.z),(m_p4.x,m_p4.y,m_p4.z))
    else:
        Vaxis=parallelEdges[0].Curve.Axis
        Vcenter=parallelEdges[0].Curve.Center
        PtDir1=Vcenter+Vaxis*LMax
        PtDir2=Vcenter-Vaxis*LMax
        Rayon=V1.distanceToLine(PtDir1,PtDir2)
        Diff=App.Vector()
        Diff.projectToLine(V1-Vcenter,Vaxis)
        Pnt=V1+Diff
        Courbe=Part.makeCircle(Rayon,Pnt,Vaxis)
    #~ Part.show(Courbe)
    Pts=[]
    #~ print ExtremFaces
    for face in ExtremFaces:
        #~ Part.show(face)
        Plane_Point=face.CenterOfMass
        
        Plane_Normal=face.normalAt(0,0)
        Plane_face=Part.makePlane(LMax*10,LMax*10,Plane_Point, Plane_Normal )
        #~ Part.show(Plane_face)
        Plane_Center = Plane_face.CenterOfMass
        Plane_Translate =  Plane_Point - Plane_Center
        Plane_face.translate( Plane_Translate )
        #~ Part.show(Plane_face)
        points=Plane_face.section(Courbe)
        #~ Part.show(points)
        
        dist=LMax/2
        #~ print dist
        #~ print points.Vertexes
        for point in points.Vertexes:
            #~ print point.Point
            #~ print Plane_Point
            #~ CreateLine(point.Point,Plane_Point,1)
            L=point.Point.distanceToPoint(Plane_Point)
            #~ print L
            
            if L<dist:
                dist=L
                
                Pt=point
                #~ print Pt
            
        Pts.append(Pt)
    #~ print Pts
    #~ CreateLine(Pts[0].Point,Pts[1].Point,1)
    
    if parallelEdges[0].curvatureAt(0.0)<=tolerance:
        X1B=Pts[0].Vertexes[0].X
        Y1B=Pts[0].Vertexes[0].Y
        Z1B=Pts[0].Vertexes[0].Z
        X2B=Pts[1].Vertexes[0].X
        Y2B=Pts[1].Vertexes[0].Y
        Z2B=Pts[1].Vertexes[0].Z
        CourbeBarre=Part.makeLine((X1B,Y1B,Z1B),(X2B,Y2B,Z2B))
    else :
        if len(Pts)==2:
            Alpha=[]
            P0=Courbe.valueAt(Courbe.FirstParameter)
            Zero=P0-Pnt
            #~ Line=Part.makeLine(((0.0,0.0,0.0)),(Zero.x,Zero.y,Zero.z))
            #~ Part.show(Line)
            for pt in Pts:
                Vtest=pt.Vertexes[0].Point
                V=pt.Vertexes[0].Point-Pnt
                #~ print V
                #~ print Zero
                Alpha.append(math.degrees(DraftVecUtils.angle(Zero,V,Vaxis)))
                #~ Line=Part.makeLine(((0.0,0.0,0.0)),(V.x,V.y,V.z))
                #~ Part.show(Line)
                #~ Line=Part.makeLine(((0.0,0.0,0.0)),(Vtest.x,Vtest.y,Vtest.z))
                #~ Part.show(Line)
            #~ print Alpha    
            #~ Line=Part.makeLine(((0.0,0.0,0.0)),((V1-Pnt).x,(V1-Pnt).y,(V1-Pnt).z))
            #~ Part.show(Line)
            Beta=math.degrees(DraftVecUtils.angle(Zero,V1-Pnt,Vaxis))
            #~ print Beta
            AlphaControle=[]
            for angle in Alpha:
                if angle <0:
                    angle=360+angle
                AlphaControle.append(angle)
            #~ print AlphaControle
            if AlphaControle[0]>Beta:
                Alpha.reverse()
            #~ print Alpha    
            CourbeBarre=Part.makeCircle(Rayon,Pnt,Vaxis,Alpha[0],Alpha[1])
        else:
            print u"Pbm"

    return CourbeBarre
    
def RotAndMoveFace(Face):
    FaceRAM=Face
    Norm=Face.normalAt(0,0)
    L=0.0
    n=0
    nLmax=0
    for edge in Face.Edges:
        if edge.Length-L>tolerance:
            L=edge.Length
            nLmax=n
        n=n+1
    Vect=Face.Edges[nLmax].tangentAt(0)
    Ptx=Face.Edges[nLmax].Vertexes[0].X
    Pty=Face.Edges[nLmax].Vertexes[0].Y
    Ptz=Face.Edges[nLmax].Vertexes[0].Z
    Pt=Base.Vector(Ptx,Pty,Ptz)
    #~ print Vect
    V=Base.Vector(0.0,0.0,0.0)
    VX=Base.Vector(1.0,0.0,0.0)
    VZ=Base.Vector(0.0,0.0,1.0)
    N=Norm.cross(VZ)
    pos=V
    center=Pt
    rot0=FreeCAD.Rotation(0.0,0.0,0.0)
    rot1=FreeCAD.Rotation(Norm,VZ)
    FaceRAM.Placement=App.Placement(pos, rot1, center).multiply(FaceRAM.Placement)
    Vect=Face.Edges[nLmax].tangentAt(0)
    Alpha=math.degrees(Vect.getAngle(VX))
    rot2=FreeCAD.Rotation(VZ,-Alpha)
    FaceRAM.Placement=App.Placement(pos, rot2, center).multiply(FaceRAM.Placement)
    mov1x=-FaceRAM.BoundBox.XMin
    mov1y=-FaceRAM.BoundBox.YMin
    mov1z=-FaceRAM.BoundBox.ZMin
    mov1=Base.Vector(mov1x,mov1y,mov1z)
    FaceRAM.Placement=App.Placement(mov1, rot0, center).multiply(FaceRAM.Placement)
        
    return FaceRAM

def RotAndMoveSol(Sol,Pt,X,Z):
    
    X=X.tangentAt(0)
    
    SolRAM=Sol.Shape.copy()
    
    #~ print SolRAM
        
    V=Base.Vector(0.0,0.0,0.0)
    VX=Base.Vector(1.0,0.0,0.0)
    VZ=Base.Vector(0.0,0.0,1.0)
    
    if abs(Z.x)-abs(VZ.x)<tolerance and abs(Z.y)-abs(VZ.y)<tolerance and abs(Z.z)-abs(VZ.z)<tolerance:
        Alpha=-math.degrees(VX.getAngle(X))
        Beta=0.0
        Gamma=0.0
    else :
        N=Z.cross(VZ)
        Alpha=-90.0+math.degrees(N.getAngle(VX))
        Beta=-math.degrees(Z.getAngle(VZ))
        Gamma=-math.degrees(N.getAngle(X))+90.0
    
    pos=V
    center=Pt
    rot0=FreeCAD.Rotation(0.0,0.0,0.0)
    rot1=FreeCAD.Rotation(Alpha,0.0,0.0)
    rot2=FreeCAD.Rotation(0.0,Beta,0.0)
    rot3=FreeCAD.Rotation(Gamma,0.0,0.0)
    
    SolRAM.Placement=App.Placement(pos, rot1, center).multiply(SolRAM.Placement)
    SolRAM.Placement=App.Placement(pos, rot2, center).multiply(SolRAM.Placement)
    SolRAM.Placement=App.Placement(pos, rot3, center).multiply(SolRAM.Placement)
    
    Longueur=SolRAM.BoundBox.XLength
    
    mov1x=-SolRAM.BoundBox.XMin
    mov1y=-SolRAM.BoundBox.YMin
    mov1z=-SolRAM.BoundBox.ZMin
    
    mov1=Base.Vector(mov1x,mov1y,mov1z)
    SolRAM.Placement=App.Placement(mov1, rot0, center).multiply(SolRAM.Placement)
    
    mov1y=-SolRAM.BoundBox.YMax/2
    mov1z=-SolRAM.BoundBox.ZMax/2
    mov1=Base.Vector(0,mov1y,mov1z)
    #~ print mov1
    SolRAM.Placement=App.Placement(mov1, rot0, center).multiply(SolRAM.Placement)
        
    Longueur=SolRAM.BoundBox.XLength
        
    #~ Part.show(SolRAM)
    
    return SolRAM,Longueur
    
    

def ProfilIPEouHE(TypeProf):
    
    profIPE=ProfIPE()
    profHE=ProfHE()
    
    Param=ParamIouH(TypeProf)
    
    TypeIPE=0
    TypeHE=0
    
    for mes in profIPE:
        if abs(Param[0]-mes[2])<=tolerance and abs(Param[1]-mes[3])<=tolerance and abs(Param[2]-mes[4])<=tolerance:
            TypeIPE=str(mes[0])    .encode('utf-8')        
        
    for mes in profHE:
        if abs(Param[0]-mes[2])<=tolerance and abs(Param[1]-mes[3])<=tolerance and abs(Param[2]-mes[4])<=tolerance:
            TypeHE=str(mes[0]).encode('utf-8')
        
    if TypeIPE!=0:
        TypeIPEouHE=u"Poutre "+str(TypeIPE).encode('utf-8')
    elif TypeHE!=0:
        TypeIPEouHE=u"Poutre "+str(TypeHE).encode('utf-8')
    else :
        TypeIPEouHE=u"h=u"+str(Param[0]).encode('utf-8')+u" b=u"+str(Param[1]).encode('utf-8')+u" tw=u"+str(Param[2]).encode('utf-8')+u" (pas en catalogue...)"
    
    return TypeIPEouHE,Param[3],Param[4]
    
def ProfilIPN(TypeProf):
    
    profIPN=ProfIPN()
        
    Param=ParamIouH(TypeProf)
    
    Test=0
    
    TypeIPN=u"Poutre IPN "
    
    for mes in profIPN:
        if abs(Param[0]-mes[1])<=tolerance and abs(Param[1]-mes[2])<=tolerance and abs(Param[2]-mes[3])<=tolerance:
            TypeIPN=TypeIPN+str(int(mes[1])).encode('utf-8')
            Test=1
     
    if Test==0:
        TypeUPN=u"Poutre IPN "+u"h=u"+str(Param[0]).encode('utf-8')+u" b=u"+str(Param[1]).encode('utf-8')+u" tw=u"+str(Param[2]).encode('utf-8')+u" (pas en catalogue...)"
    
    return TypeIPN,Param[3],Param[4]

def ProfilUPN(TypeProf):

    profUPN=ProfUPN()
    
    Param=ParamUPN(TypeProf)
    
    Test=0
    
    for mes in profUPN:
        if abs(Param[0]-mes[1])<=tolerance and abs(Param[1]-mes[2])<=tolerance and abs(Param[2]-mes[3])<=tolerance :
            TypeUPN=u"Poutre UPN "+str(mes[1]).encode('utf-8')
            Test=1

    if Test==0:
        TypeUPN=u"Poutre UPN "+u"h=u"+str(Param[0]).encode('utf-8')+u" b=u"+str(Param[1]).encode('utf-8')+u" tw=u"+str(Param[2]).encode('utf-8')+u" (pas en catalogue...)"
    
    
    return TypeUPN,Param[3],Param[4]
    
def ProfilUPE(TypeProf):
    
    profUPE=ProfUPE()
    
    Param=ParamUPE(TypeProf)
    
    Test=0
    
    for mes in profUPE:
        if abs(Param[0]-mes[1])<=tolerance and abs(Param[1]-mes[2])<=tolerance and abs(Param[2]-mes[4])<=tolerance :
            TypeUPE=u"Poutre UPE "+str(mes[1]).encode('utf-8')
            Test=1

    if Test==0:
        TypeUPE=u"Poutre UPE "+u"h=u"+str(Param[0]).encode('utf-8')+u" b=u"+str(Param[1]).encode('utf-8')+u" tw=u"+str(Param[2]).encode('utf-8')+u" (pas en catalogue...)"
    
    
    return TypeUPE,Param[3],Param[4]
    
def ProfilCorniere(TypeProf):

    profCorniereEgaleAcier=ProfCorniereEgaleAcier()
    profCorniereInegaleAcier=ProfCorniereInegaleAcier()

    Param=ParamCorniereAcier(TypeProf)

    TypeCorniere=u"Profil Cornière "
    Test=0

    if Param[0]-Param[1]<tolerance:
        TypeCorniere=TypeCorniere+u"égale "
        for mes in profCorniereEgaleAcier:
            if abs(Param[0]-mes[1])<=tolerance and abs(Param[2]-mes[2])<=tolerance :
                TypeCorniere=TypeCorniere+str(mes[1]).encode('utf-8')+u" x "+str(mes[1]).encode('utf-8')+u" ép. "+str(mes[2]).encode('utf-8')
                Test=1
    else :
        TypeCorniere=TypeCorniere+u"inégale "
        for mes in profCorniereInegaleAcier:
            if abs(Param[0]-mes[1])<=tolerance and abs(Param[1]-mes[2])<=tolerance and abs(Param[2]-mes[3])<=tolerance :
                TypeCorniere=TypeCorniere+str(mes[1]).encode('utf-8')+u" x "+str(mes[2]).encode('utf-8')+u" ép. "+str(mes[3]).encode('utf-8')
                Test=1
                
    if Test==0:
        TypeCorniere=TypeCorniere+u"h=u"+str(Param[0]).encode('utf-8')+u" b=u"+str(Param[1]).encode('utf-8')+u" t=u"+str(Param[2]).encode('utf-8')+u" (pas en catalogue...)"

    return TypeCorniere,Param[3],Param[4]

def ProfilPlatCarre(TypeProf):    

    profPlat=ProfPlat()
    profCarre=ProfCarre()
    
    Param=ParamPlatCarre(TypeProf)
    
    Test=0
    
    if Param[2]==u"Carré":
        for mes in profCarre:
            if abs(Param[0]-mes[0])<=tolerance and abs(Param[1]-mes[0])<=tolerance :
                TypePlatCarre=u"Profil carré "+str(mes[0]).encode('utf-8')+u" x "+str(mes[0]).encode('utf-8')
                Test=1
    else:
        n=0
        nep=0
        for ep in profPlat[0]:
            if abs(ep-Param[1])<=tolerance:
                nep=n
            n=n+1                
        n=0
        lla=0
        for largeur in profPlat:
            if abs(largeur[0]-Param[0])<=tolerance:
                lla=n
            n=n+1
        if profPlat[lla][nep]>0 and lla!=0:
            #~ print profPlat[lla][nep]
            TypePlatCarre=u"Profil plat "+str(profPlat[0][nep]).encode('utf-8')+u" x "+str(profPlat[lla][0]).encode('utf-8')
            Test=1
    
    if Test==0:
        TypePlatCarre=u"Profil "+str(Param[2]).encode('utf-8')+u" : "+str(Param[0]).encode('utf-8')+u" x "+str(Param[1]).encode('utf-8')

    return TypePlatCarre,Param[3],Param[4]

def ProfilTe(TypeProf):

    profTe=ProfTe()
    
    Param=ParamTe(TypeProf)
    
    Test=0
    
    if abs(Param[0]-Param[1])<=tolerance:
        TypeTe=u"Profil Té symétriques égaux à angles arrondis "
    else:
        TypeTe=u"Profil Té symétriques inégaux à angles arrondis "
    
    for mes in profTe:
        if abs(Param[0]-mes[0])<=tolerance and abs(Param[1]-mes[1])<=tolerance :
            TypeTe=TypeTe+str(mes[0]).encode('utf-8')+u" x "+str(mes[1]).encode('utf-8')
            Test=1
    
    if Test==0:
        TypeTe=TypeTe+str(mes[0]).encode('utf-8')+u" x "+str(mes[1]).encode('utf-8')+u" (pas en catalogue...)"

    return TypeTe,Param[2],Param[3]

def ProfilRond(TypeProf):

    profRond=ProfRond()

    Param=ParamRond(TypeProf)
    
    TypeRond=u"Profil Rond Diamètre "
    
    Test=0

    for mes in profRond:
        
        if abs(Param[0]-mes[1])<=tolerance :
            TypeRond=TypeRond+str(mes[1]).encode('utf-8')
            Test=1
         
    if Test==0:
        TypeRond=TypeRond+str(Param[0]).encode('utf-8')+u" (pas en catalogue...)"

    return TypeRond,Param[1],Param[2]

def ProfilTubeRond(TypeProf):
    
    profTubeRond=ProfTubeRond()
    
    Param=ParamTubeRond(TypeProf)
    
    Test=0
    
    for mes in profTubeRond[0]:
        if abs(Param[0]-mes[0])<=tolerance and abs(Param[2]-mes[1])<=tolerance :
            
            TypeTubeRond=profTubeRond[1][3*mes[4]-3]+u"\n"
            TypeTubeRond=TypeTubeRond+profTubeRond[1][3*mes[4]-2]+u"\n"
            TypeTubeRond=TypeTubeRond+profTubeRond[1][3*mes[4]-1]+u"\n"
            TypeTubeRond=TypeTubeRond+u"Diamètre "+str(mes[0]).encode('utf-8')+u", épaisseur "+str(mes[1]).encode('utf-8')+\
" ,Diamètre intérieur "+str(2*(mes[0]/2-mes[1])).encode('utf-8')
            Test=1
    
    if Test==0:
        TypeTubeRond=u"Profil Tube Rond Diamètre "+str(Param[0]).encode('utf-8')+u", épaisseur "+str(Param[2]).encode('utf-8')+u"\
, Diamètre intérieur "+str(Param[1]).encode('utf-8')+u"\n(pas en catalogue...)"

    return TypeTubeRond,Param[3],Param[4]

def ProfilTubeCarreRectangle(TypeProf):

    #~ profTubeCarre=ProfTubeCarre()
    #~ 
    #~ profTubeRectangle=ProfTubeRectangle()
    
    Param=ParamTubeCarreRectangle(TypeProf)
        
    Test=0
    
    if Test==0:
        if Param[0]==Param[1]:
            TypeTubeCarreRectangle=u"Profil Tube carré "
        else :
            TypeTubeCarreRectangle=u"Profil Tube rectangle "
        TypeTubeCarreRectangle=TypeTubeCarreRectangle+str(Param[1]).encode('utf-8')+u" x "+str(Param[0]).encode('utf-8')+u", épaisseur : "+str(Param[2]).encode('utf-8')

    return TypeTubeCarreRectangle,Param[3],Param[4]

def ProfilLAlu(TypeProf):
    
    Param=ParamLAlu(TypeProf)
        
    Test=0
    
    if Test==0:
        if Param[0]==Param[1]:
            TypeLAlu=u"Profil cornière aluminium égale "
        else :
            TypeLAlu=u"Profil cornière aluminium inégale "
        
        
        TypeLAlu=TypeLAlu+str(Param[0]).encode('utf-8')+u" x "+str(Param[1]).encode('utf-8')+u", épaisseur : "+str(Param[2]).encode('utf-8')
    
    return TypeLAlu,Param[3],Param[4]

def ProfilTouUAlu(TypeProf):
    
    TypeTouUAlu=u"Té ou U Alu (Reste à faire...) "
    
    return TypeTouUAlu,Param[3],Param[4]

def ProfilTubeCarreRectangleAlu(TypeProf):
    
    Param=ParamTubeCarreRectangleAlu(TypeProf)
        
    Test=0
    
    if Test==0:
        if Param[0]==Param[1]:
            TypeTubeCarreRectangleAlu=u"Profil Tube carré aluminium "
        else :
            TypeTubeCarreRectangleAlu=u"Profil Tube rectangle aluminium "
        TypeTubeCarreRectangleAlu=TypeTubeCarreRectangleAlu+str(Param[0]).encode('utf-8')+u" x "+str(Param[1]).encode('utf-8')+u", épaisseur : "+str(Param[2]).encode('utf-8')

    return TypeTubeCarreRectangleAlu,Param[3],Param[4]
    
def ProfilUPAFAcier(TypeProf):
    
    Param=ParamUPAF(TypeProf)
        
    Test=0
    
    if Test==0:
        TypeUPAFAcier=u"En travaux Profil UPAF (coulisse) "+str(Param[0]).encode('utf-8')+u" x "+str(Param[1]).encode('utf-8')+u", épaisseur : "+str(Param[2]).encode('utf-8')
        
    return TypeUPAFAcier,Param[3],Param[4]
        
def FamilleProfile(NbArretes,ProfilOuvert,NbArretesDroites,NbLgArrDiff):
    
    Famille=[[16,1,12,[4],"IPE IPEA HEA HEB HEM",1],\
    [20,1,12,[4],"IPN",2],\
    [12,1,8,[5],"UPN",3],\
    [10,1,8,[5],"UPE",4],\
    [9,1,6,[3,4,5],"Corniere Acier",5],\
    [4,1,4,[1,2],"Plat Carre",6],\
    [14,1,8,[4,5],"Te",7],\
    [1,1,0,[0],"Rond",8],\
    [2,2,0,[0],"Tube Rond",9],\
    [4,2,0,[0],"Tube Rond",9],\
    [16,2,8,[1,2],"Tube Carre Rectangle acier",10],\
    [6,1,6,[3,4,5],"Profil L Alu",11],\
    [8,1,8,[3,4,5],"Profil U T Alu",12],\
    [8,2,8,[2,3,4],"Tube Carre Rectangle Alu",13],\
    [12,1,8,[2,3],"UPAF acier",14]]
    
    #~ print NbArretes
    #~ print ProfilOuvert
    #~ print NbArretesDroites
    #~ print NbLgArrDiff
    
    
    
    TypeProfil=False
    for f in Famille:
        if f[0]==NbArretes and f[1]==ProfilOuvert and f[2]==NbArretesDroites:
            for n in f[3]:
                if NbLgArrDiff==n:
                    TypeProfil=f
    
    return TypeProfil
    
oldDocumentObjects=App.ActiveDocument.Objects
    
Selection=FreeCADGui.Selection.getSelection()
sel=[]
cpt=0
for Obj in Selection:
    if cpt==0:
        sel.append(Obj)
    else:
        Test=0
        cpt2=0
        for Obj2 in Selection:
            if cpt!=cpt2: 
                if Obj2==Obj:
                    Test=Test+1
            cpt2=cpt2+1
        if Test<2:    
            sel.append(Obj)
            
    cpt=cpt+1

if sel:
    Sections=[]
    TypeSections=[]
    Axes=[]
    Plaques=[]
    for solide in sel:
        typeSol=TypeSol(solide)
        #~ print solide.Label
            
        if typeSol[0]==1:#Poutre
            Sections.append(GetSection(solide,typeSol[4],typeSol[5],typeSol[6],typeSol[7]))
        if typeSol[0]==2:#Suite de poutre (tuyauterie)
            Sections.append(GetSection(solide))
        if typeSol[0]==3:#Plaque
            Plaques.append(GetInfoPlaque(solide,typeSol[2],typeSol[3]))
    #~ print Sections
    #~ print Sections
    #~ Sections.sort(None,None,False)
    #~ print Sections
    if len(Sections)>=1:
        for section in Sections:
            if section[2]==True:
                TypeSections.append(TypeSection(section[0]))
                #[Section,HighLength,TestBarre,ExtremFaces,Label,ParallelEdges]
                sect=section[0]
                ExtFaces=section[3]
                HighLength=section[1]
                ParallelEdges=section[5]
                
                #~ print TypeSections
                PointAxe=TypeSections[len(TypeSections)-1][1]
                Axes.append([TraceAxeBArre(sect,ExtFaces,PointAxe,HighLength,ParallelEdges),section[4]])
                
                
                # Sortir tous les Zaxis des profil avant de décomenter la suite.
                ZEdgeSection=TypeSections[len(TypeSections)-1][2]
                RotAndMoveSol(section[6],PointAxe,ParallelEdges[0],ZEdgeSection)
                
        for axe in Axes:
            #~ print axe[0]
            #~ print axe[1]
            NomAxe=u"Axe "+axe[1].encode('utf-8')
            show(axe[0],NomAxe)
    #~ print TypeSections
    #~ print Sections
    n=0
    if len(Sections)>=1:
        for section in Sections:
            if TypeSections[n]==0:
                print u"problème"
            else :
                print section[4]
                print TypeSections[n][0]+u" Longueur : "+str(float(int(section[1]*100+0.49))/100).encode('utf-8')+u" mm"
            n=n+1
    
    print Plaques
    sorted(Plaques,key=lambda epaisseur: epaisseur[2])
    print Plaques
    
    
    if len(Plaques)>=1:
        for plaque in Plaques:
            RotAndMoveFace(plaque[0])
            #Rapatrie le nom du Label de la plaque
            print u"---------------------"
            print plaque[1].encode('utf-8')
            Surface=plaque[0].Area
            Epaisseur=plaque[2]
            Volume=Surface*Epaisseur
            DensiteAcier=7.88
            Masse=DensiteAcier*Volume/1000000
            MasseSansDensite=Volume/1000000
            Longueur_Coupe_plaque=Longueur_Coupe(plaque[0])
            #Rapatrie l'épaisseur de la plaque
            Epaisseur=str(float(int(Epaisseur*100+0.49))/100).encode('utf-8')
            print u"Epaisseur : "+Epaisseur+u" mm"
            print u"Masse (Acier) : "+str(float(int(Masse*100+0.49))/100).encode('utf-8')+u" kg"
            print u"Masse (Densité 1) : "+str(float(int(MasseSansDensite*100+0.49))/100).encode('utf-8')+u" kg"
            print u"Surface : "+str(float(int(Surface/1000000*100+0.49))/100).encode('utf-8')+u" m²"
            print u"Longueur de coupe : "+str(float(int(Longueur_Coupe_plaque/1000*100+0.49))/100).encode('utf-8')+u" m"
            for hole in plaque[3]:
                if hole[1]>1:
                    s=u"s"
                else:
                    s=u""
                print str(hole[1]).encode('utf-8')+u" Trou"+s+u" Diamètre "+str(hole[0]).encode('utf-8')+u" mm"
            for oblongHole in plaque[4]:
                if oblongHole[1]>1:
                    s=u"s"
                else:
                    s=u""
                print str(oblongHole[0]).encode('utf-8')+u" Trou"+s+u" oblong"+s+u" Diamètre "+str(oblongHole[1]).encode('utf-8')+u" Longueur "+str(oblongHole[2]).encode('utf-8')
            
            print u"---------------------"
            
            
            Ep=u" ép "
            name="Plaque "+plaque[1]+Ep+Epaisseur
            obj=show(plaque[0],name)
            Nom_fichier_dxf=Construction_Nom_Plaque(plaque)
            Export_vers_dxf(obj,Nom_fichier_dxf)
            #Identifier les plaques identiques
            
        
        
else:
    print u"Sélectionner des pièces"
